; NLCS Opentool - Auto-generated layer data
; Do NOT edit manually - regenerate with nlcs_generate_lisp.py

(setq *nlcs-layers* (list))
(setq *nlcs-disciplines* (list))

; Discipline definitions
(setq *nlcs-disciplines* (list
  (cons "AL" "Algemeen")
  (cons "AM" "Assen en metrering")
  (cons "BC" "Betonconstructies")
  (cons "BV" "Bermbeveiliging")
  (cons "FC" "Funderingsconstructies")
  (cons "FV" "Faunavoorzieningen")
  (cons "GC" "Grondkerende constructies")
  (cons "GK" "Grondkeringen")
  (cons "GR" "Groen")
  (cons "GW" "Grondwerken")
  (cons "HU" "Hulpconstructies")
  (cons "IE" "Inrichtingselementen")
  (cons "IV" "Installaties Vaarweg")
  (cons "IW" "Installaties Wegen")
  (cons "KC" "Kunststofconstructies")
  (cons "KG" "Kadastrale grenzen")
  (cons "KL" "Kabels en leidingen")
  (cons "KW" "Kunstwerken")
  (cons "MC" "Mechanische constructies")
  (cons "MO" "Milieuonderzoek")
  (cons "MW" "Metselwerk")
  (cons "OB" "Oever- en bodembescherming")
  (cons "OG" "Ondergrond")
  (cons "OV" "Openbare verlichting")
  (cons "RI" "Riolering")
  (cons "SC" "Staalconstructies")
  (cons "VH" "Verhardingen")
  (cons "VV" "Verkeersmaatregelen Vaarweg")
  (cons "VW" "Verkeersmaatregelen Weg")
  (cons "WH" "Waterhuishouding")
  (cons "ZZ" "Diversen")
))

; Layer data per discipline (id, omschrijving, kleur, lijngewicht, lijntype)
; Algemeen (AL) - 33 lagen
(setq *nlcs-layers* (cons (list "AL" "Algemeen" (list
  (list "20" "AL-TEKENBLAD_SCHAALBALK" 7 0.18 "CONTINUOUS" "12" "G/S")
  (list "12" "AL-TEKENBLAD" 7 0.25 "CONTINUOUS" "" "S")
  (list "3364" "AL-COORDINAATPUNT" 7 0.25 "CONTINUOUS" "" "G/S")
  (list "27" "AL-VERWIJZING" 7 0.18 "CONTINUOUS" "" "G/S")
  (list "10" "AL-ORIENTATIE" 7 0.18 "CONTINUOUS" "" "S")
  (list "1" "AL-AANKLEDING" 2 0.35 "CONTINUOUS" "" "G/S")
  (list "15" "AL-TEKENBLAD_KADER" 7 0.7 "CONTINUOUS" "12" "G")
  (list "25" "AL-TEKENBLAD_VIEWPORT" 7 0.18 "CONTINUOUS" "12" "G")
  (list "13" "AL-TEKENBLAD_DEELKADER" 7 0.18 "CONTINUOUS" "12" "G")
  (list "22" "AL-TEKENBLAD_TITELBLOK" 7 0.25 "CONTINUOUS" "12" "G")
  (list "26" "AL-TEKENBLAD_WIJZIGINGSBLOK" 7 0.25 "CONTINUOUS" "12" "G")
  (list "21" "AL-TEKENBLAD_SITUATIE" 7 0.18 "CONTINUOUS" "12" "G")
  (list "14" "AL-TEKENBLAD_HULPLIJN" 7 0.18 "CONTINUOUS" "12" "G")
  (list "24" "AL-TEKENBLAD_VERKLARING" 7 0.18 "CONTINUOUS" "12" "G")
  (list "29" "AL-VERWIJZING_DETAIL" 7 0.35 "AL-DETAILS-SO" "27" "G")
  (list "31" "AL-VERWIJZING_WIJZIGING" 7 0.18 "ZZ-CENTER-SO" "27" "G")
  (list "30" "AL-VERWIJZING_DOORSNEDE" 7 0.18 "ZZ-CENTER-SO" "27" "G")
  (list "28" "AL-VERWIJZING_AANZICHT" 7 0.18 "AL-PROFIEL-SO" "27" "G")
  (list "4" "AL-BLADVERWIJZING_BLAD" 7 0.35 "CONTINUOUS" "2" "G")
  (list "7" "AL-BLADVERWIJZING_KAART" 7 0.18 "CONTINUOUS" "2" "G")
  (list "3" "AL-BLADVERWIJZING_AS" 7 0.25 "CONTINUOUS" "2" "G")
  (list "5" "AL-BLADVERWIJZING_CONTOUR" 7 0.35 "CONTINUOUS" "2" "G")
  (list "6" "AL-BLADVERWIJZING_DTM" 7 0.18 "CONTINUOUS" "2" "G")
  (list "16" "AL-TEKENBLAD_KADER_AFSNIJMARKERING" 7 0.25 "CONTINUOUS" "15" "G")
  (list "18" "AL-TEKENBLAD_KADER_ROOSTERVERDELING" 7 0.25 "CONTINUOUS" "15" "G")
  (list "17" "AL-TEKENBLAD_KADER_CENTERMARKERING" 7 0.25 "CONTINUOUS" "15" "G")
  (list "19" "AL-TEKENBLAD_KADER_VOUWMERK" 7 0.18 "CONTINUOUS" "15" "G")
  (list "23" "AL-TEKENBLAD_TITELBLOK_BEDRIJFSLOGO" 7 0.25 "CONTINUOUS" "22" "G")
  (list "34" "AL-PROFIELBALK" 7 0.25 "CONTINUOUS" "" "G")
  (list "11" "AL-REFERENTIE" 7 0.18 "CONTINUOUS" "" "G")
  (list "2" "AL-BLADVERWIJZING" 7 0.18 "CONTINUOUS" "" "G")
  (list "38" "AL-TEKENBLADGRENS" 7 0.35 "AL-TEKENBLADGRENS-SO" "" "G")
  (list "32" "AL-LEGENDA" 7 0.18 "CONTINUOUS" "" "G")
)) *nlcs-layers*))

; Assen en metrering (AM) - 118 lagen
(setq *nlcs-layers* (cons (list "AM" "Assen en metrering" (list
  (list "40" "AM-AS" 10 0.18 "AM-AS-SO" "" "G/S")
  (list "89" "AM-AS_WATERWEG" 10 0.18 "AM-AS-SO" "40" "G")
  (list "95" "AM-AS_KUNSTWERK" 10 0.18 "AM-AS-SO" "40" "G")
  (list "42" "AM-AS_WEG" 10 0.18 "AM-AS-SO" "40" "G")
  (list "41" "AM-AS_PUNTNUMMER" 10 0.18 "AM-AS-SO" "40" "G/S")
  (list "139" "AM-AS_WATERGANG" 10 0.18 "AM-AS-SO" "40" "G")
  (list "79" "AM-AS_PAD" 10 0.18 "AM-AS-SO" "40" "G")
  (list "137" "AM-AS_KADE" 10 0.18 "AM-AS-SO" "40" "G")
  (list "3090" "AM-AS_WATERKERING" 10 0.18 "AM-AS-SO" "40" "G")
  (list "87" "AM-AS_SPOOR" 10 0.18 "AM-AS-SO" "40" "G")
  (list "142" "AM-AS_WAL" 10 0.18 "AM-AS-SO" "40" "G")
  (list "143" "AM-AS_CUNET" 10 0.18 "AM-AS-SO" "40" "G")
  (list "133" "AM-AS_BERMBEVEILIGINGSVOORZIENING" 10 0.18 "AM-AS-SO" "40" "G")
  (list "3365" "AM-AS_KERING" 10 0.18 "AM-AS-SO" "40" "G")
  (list "134" "AM-AS_DIJK" 10 0.18 "AM-AS-SO" "40" "G")
  (list "132" "AM-AS_GRONDKERENDECONSTRUCTIE" 10 0.18 "AM-AS-SO" "40" "G")
  (list "147" "AM-STRING_GDS" 170 0.18 "AM-AS-SO" "145" "G")
  (list "146" "AM-STRING_MASTER" 170 0.18 "AM-AS-SO" "145" "G")
  (list "148" "AM-STRING_HULP" 170 0.18 "AM-AS-SO" "145" "G")
  (list "92" "AM-AS_WATERWEG_VAARGEUL" 10 0.18 "AM-AS-SO" "89" "G")
  (list "93" "AM-AS_WATERWEG_NEVENGEUL" 10 0.18 "AM-AS-SO" "89" "G")
  (list "91" "AM-AS_WATERWEG_NEVENVAARWEG" 10 0.18 "AM-AS-SO" "89" "G")
  (list "3091" "AM-AS_WATERWEG_BEEK" 10 0.18 "AM-AS-SO" "89" "G")
  (list "94" "AM-AS_WATERWEG_KANAAL" 10 0.18 "AM-AS-SO" "89" "G")
  (list "90" "AM-AS_WATERWEG_HOOFDVAARWEG" 10 0.18 "AM-AS-SO" "89" "G")
  (list "3092" "AM-AS_WATERWEG_GRACHT" 10 0.18 "AM-AS-SO" "89" "G")
  (list "3093" "AM-AS_WATERWEG_RIVIER" 10 0.18 "AM-AS-SO" "89" "G")
  (list "123" "AM-AS_KUNSTWERK_SLUIS" 10 0.18 "AM-AS-SO" "95" "G")
  (list "96" "AM-AS_KUNSTWERK_VIADUCT" 10 0.18 "AM-AS-SO" "95" "G")
  (list "101" "AM-AS_KUNSTWERK_TUNNEL" 10 0.18 "AM-AS-SO" "95" "G")
  (list "110" "AM-AS_KUNSTWERK_BRUG" 10 0.18 "AM-AS-SO" "95" "G")
  (list "116" "AM-AS_KUNSTWERK_WILDWISSEL" 10 0.18 "AM-AS-SO" "95" "G")
  (list "106" "AM-AS_KUNSTWERK_TUNNELBAK" 10 0.18 "AM-AS-SO" "95" "G")
  (list "109" "AM-AS_KUNSTWERK_AQUADUCT" 10 0.18 "AM-AS-SO" "95" "G")
  (list "131" "AM-AS_KUNSTWERK_GELUIDSWERENDEVOORZIENING" 10 0.18 "AM-AS-SO" "95" "G")
  (list "122" "AM-AS_KUNSTWERK_FLYOVER" 10 0.18 "AM-AS-SO" "95" "G")
  (list "130" "AM-AS_KUNSTWERK_STUW" 10 0.18 "AM-AS-SO" "95" "G")
  (list "115" "AM-AS_KUNSTWERK_DUIKER" 10 0.18 "AM-AS-SO" "95" "G")
  (list "71" "AM-AS_WEG_ONDERHOUDSWEG" 10 0.18 "AM-AS-SO" "42" "G")
  (list "59" "AM-AS_WEG_GEBIEDSONTSLUITINGSWEG" 10 0.18 "AM-AS-SO" "42" "G")
  (list "51" "AM-AS_WEG_PARALLELWEG" 10 0.18 "AM-AS-SO" "42" "G")
  (list "75" "AM-AS_WEG_EIGENWEG" 10 0.18 "AM-AS-SO" "42" "G")
  (list "47" "AM-AS_WEG_VERBINDINGSWEG" 10 0.18 "AM-AS-SO" "42" "G")
  (list "67" "AM-AS_WEG_ERFTOEGANGSWEG" 10 0.18 "AM-AS-SO" "42" "G")
  (list "63" "AM-AS_WEG_STROOMWEG" 10 0.18 "AM-AS-SO" "42" "G")
  (list "43" "AM-AS_WEG_HOOFDRIJBAAN" 10 0.18 "AM-AS-SO" "42" "G")
  (list "55" "AM-AS_WEG_BUSBAAN" 10 0.18 "AM-AS-SO" "42" "G")
  (list "140" "AM-AS_WATERGANG_SLOOT" 10 0.18 "AM-AS-SO" "139" "G")
  (list "141" "AM-AS_WATERGANG_GREPPEL" 10 0.18 "AM-AS-SO" "139" "G")
  (list "80" "AM-AS_PAD_FIETSPAD" 10 0.18 "AM-AS-SO" "79" "G")
  (list "83" "AM-AS_PAD_VOETPAD" 10 0.18 "AM-AS-SO" "79" "G")
  (list "86" "AM-AS_PAD_RUITERPAD" 10 0.18 "AM-AS-SO" "79" "G")
  (list "3088" "AM-AS_SPOOR_METRO" 10 0.18 "AM-AS-SO" "87" "G")
  (list "3089" "AM-AS_SPOOR_TRAM" 10 0.18 "AM-AS-SO" "87" "G")
  (list "4033" "AM-AS_SPOOR_TREIN" 10 0.18 "AM-AS-SO" "87" "G")
  (list "4034" "AM-AS_SPOOR_KRAAN" 10 0.18 "AM-AS-SO" "87" "G")
  (list "88" "AM-AS_SPOOR_RAIL" 10 0.18 "AM-AS-SO" "87" "G")
  (list "136" "AM-AS_DIJK_WINTERDIJK" 10 0.18 "AM-AS-SO" "134" "G")
  (list "135" "AM-AS_DIJK_ZOMERDIJK" 10 0.18 "AM-AS-SO" "134" "G")
  (list "125" "AM-AS_KUNSTWERK_SLUIS_UITWATERINGSSLUIS" 10 0.18 "AM-AS-SO" "123" "G")
  (list "124" "AM-AS_KUNSTWERK_SLUIS_SCHUTSLUIS" 10 0.18 "AM-AS-SO" "123" "G")
  (list "126" "AM-AS_KUNSTWERK_SLUIS_INLAATSLUIS" 10 0.18 "AM-AS-SO" "123" "G")
  (list "128" "AM-AS_KUNSTWERK_SLUIS_KEERSLUIS" 10 0.18 "AM-AS-SO" "123" "G")
  (list "127" "AM-AS_KUNSTWERK_SLUIS_INNUNDATIESLUIS" 10 0.18 "AM-AS-SO" "123" "G")
  (list "129" "AM-AS_KUNSTWERK_SLUIS_TIJSLUIS" 10 0.18 "AM-AS-SO" "123" "G")
  (list "98" "AM-AS_KUNSTWERK_VIADUCT_SPOOR" 10 0.18 "AM-AS-SO" "96" "G")
  (list "97" "AM-AS_KUNSTWERK_VIADUCT_WEG" 10 0.18 "AM-AS-SO" "96" "G")
  (list "100" "AM-AS_KUNSTWERK_VIADUCT_VOETGANGER" 10 0.18 "AM-AS-SO" "96" "G")
  (list "99" "AM-AS_KUNSTWERK_VIADUCT_FIETS" 10 0.18 "AM-AS-SO" "96" "G")
  (list "104" "AM-AS_KUNSTWERK_TUNNEL_FIETS" 10 0.18 "AM-AS-SO" "101" "G")
  (list "103" "AM-AS_KUNSTWERK_TUNNEL_SPOOR" 10 0.18 "AM-AS-SO" "101" "G")
  (list "105" "AM-AS_KUNSTWERK_TUNNEL_VOETGANGER" 10 0.18 "AM-AS-SO" "101" "G")
  (list "102" "AM-AS_KUNSTWERK_TUNNEL_WEG" 10 0.18 "AM-AS-SO" "101" "G")
  (list "111" "AM-AS_KUNSTWERK_BRUG_WEG" 10 0.18 "AM-AS-SO" "110" "G")
  (list "112" "AM-AS_KUNSTWERK_BRUG_SPOOR" 10 0.18 "AM-AS-SO" "110" "G")
  (list "113" "AM-AS_KUNSTWERK_BRUG_FIETS" 10 0.18 "AM-AS-SO" "110" "G")
  (list "114" "AM-AS_KUNSTWERK_BRUG_VOETGANGER" 10 0.18 "AM-AS-SO" "110" "G")
  (list "117" "AM-AS_KUNSTWERK_WILDWISSEL_ECODUCT" 10 0.18 "AM-AS-SO" "116" "G")
  (list "119" "AM-AS_KUNSTWERK_WILDWISSEL_ECOTUNNEL" 10 0.18 "AM-AS-SO" "116" "G")
  (list "107" "AM-AS_KUNSTWERK_TUNNELBAK_WEG" 10 0.18 "AM-AS-SO" "106" "G")
  (list "108" "AM-AS_KUNSTWERK_TUNNELBAK_SPOOR" 10 0.18 "AM-AS-SO" "106" "G")
  (list "74" "AM-AS_WEG_ONDERHOUDSWEG_OVERGANG" 130 0.18 "AM-AS-SO" "71" "G")
  (list "72" "AM-AS_WEG_ONDERHOUDSWEG_RECHT" 50 0.18 "AM-AS-SO" "71" "G")
  (list "73" "AM-AS_WEG_ONDERHOUDSWEG_CIRKEL" 90 0.18 "AM-AS-SO" "71" "G")
  (list "62" "AM-AS_WEG_GEBIEDSONTSLUITINGSWEG_OVERGANG" 130 0.18 "AM-AS-SO" "59" "G")
  (list "61" "AM-AS_WEG_GEBIEDSONTSLUITINGSWEG_CIRKEL" 90 0.18 "AM-AS-SO" "59" "G")
  (list "60" "AM-AS_WEG_GEBIEDSONTSLUITINGSWEG_RECHT" 50 0.18 "AM-AS-SO" "59" "G")
  (list "52" "AM-AS_WEG_PARALLELWEG_RECHT" 50 0.18 "AM-AS-SO" "51" "G")
  (list "53" "AM-AS_WEG_PARALLELWEG_CIRKEL" 90 0.18 "AM-AS-SO" "51" "G")
  (list "54" "AM-AS_WEG_PARALLELWEG_OVERGANG" 130 0.18 "AM-AS-SO" "51" "G")
  (list "77" "AM-AS_WEG_EIGENWEG_CIRKEL" 90 0.18 "AM-AS-SO" "75" "G")
  (list "78" "AM-AS_WEG_EIGENWEG_OVERGANG" 130 0.18 "AM-AS-SO" "75" "G")
  (list "76" "AM-AS_WEG_EIGENWEG_RECHT" 50 0.18 "AM-AS-SO" "75" "G")
  (list "50" "AM-AS_WEG_VERBINDINGSWEG_OVERGANG" 130 0.18 "AM-AS-SO" "47" "G")
  (list "49" "AM-AS_WEG_VERBINDINGSWEG_CIRKEL" 90 0.18 "AM-AS-SO" "47" "G")
  (list "48" "AM-AS_WEG_VERBINDINGSWEG_RECHT" 50 0.18 "AM-AS-SO" "47" "G")
  (list "68" "AM-AS_WEG_ERFTOEGANGSWEG_RECHT" 50 0.18 "AM-AS-SO" "67" "G")
  (list "70" "AM-AS_WEG_ERFTOEGANGSWEG_OVERGANG" 130 0.18 "AM-AS-SO" "67" "G")
  (list "69" "AM-AS_WEG_ERFTOEGANGSWEG_CIRKEL" 90 0.18 "AM-AS-SO" "67" "G")
  (list "65" "AM-AS_WEG_STROOMWEG_CIRKEL" 90 0.18 "AM-AS-SO" "63" "G")
  (list "66" "AM-AS_WEG_STROOMWEG_OVERGANG" 130 0.18 "AM-AS-SO" "63" "G")
  (list "64" "AM-AS_WEG_STROOMWEG_RECHT" 50 0.18 "AM-AS-SO" "63" "G")
  (list "45" "AM-AS_WEG_HOOFDRIJBAAN_CIRKEL" 90 0.18 "AM-AS-SO" "43" "G")
  (list "46" "AM-AS_WEG_HOOFDRIJBAAN_OVERGANG" 130 0.18 "AM-AS-SO" "43" "G")
  (list "44" "AM-AS_WEG_HOOFDRIJBAAN_RECHT" 50 0.18 "AM-AS-SO" "43" "G")
  (list "56" "AM-AS_WEG_BUSBAAN_RECHT" 50 0.18 "AM-AS-SO" "55" "G")
  (list "58" "AM-AS_WEG_BUSBAAN_OVERGANG" 130 0.18 "AM-AS-SO" "55" "G")
  (list "57" "AM-AS_WEG_BUSBAAN_CIRKEL" 90 0.18 "AM-AS-SO" "55" "G")
  (list "81" "AM-AS_PAD_FIETSPAD_RECHT" 50 0.18 "AM-AS-SO" "80" "G")
  (list "82" "AM-AS_PAD_FIETSPAD_CIRKEL" 90 0.18 "AM-AS-SO" "80" "G")
  (list "85" "AM-AS_PAD_VOETPAD_CIRKEL" 90 0.18 "AM-AS-SO" "83" "G")
  (list "84" "AM-AS_PAD_VOETPAD_RECHT" 50 0.18 "AM-AS-SO" "83" "G")
  (list "118" "AM-AS_KUNSTWERK_WILDWISSEL_ECODUCT_WILDVIADUCT" 10 0.18 "AM-AS-SO" "117" "G")
  (list "121" "AM-AS_KUNSTWERK_WILDWISSEL_ECOTUNNEL_WILDTUNNEL" 10 0.18 "AM-AS-SO" "119" "G")
  (list "120" "AM-AS_KUNSTWERK_WILDWISSEL_ECOTUNNEL_VEETUNNEL" 10 0.18 "AM-AS-SO" "119" "G")
  (list "149" "AM-KILOMETRERING" 7 0.18 "CONTINUOUS" "" "G")
  (list "150" "AM-TANGENTPUNT" 7 0.18 "CONTINUOUS" "" "G")
  (list "145" "AM-STRING" 170 0.18 "AM-AS-SO" "" "G")
)) *nlcs-layers*))

; Betonconstructies (BC) - 37 lagen
(setq *nlcs-layers* (cons (list "BC" "Betonconstructies" (list
  (list "2727" "BC-WAPENING" 170 0.18 "CONTINUOUS" "" "G/S")
  (list "2732" "BC-VOORSPANNING" 180 0.18 "CONTINUOUS" "" "G/S")
  (list "2742" "BC-AANGRENZENDE CONSTRUCTIE_HOUT" 7 0.18 "CONTINUOUS" "2740" "G/A")
  (list "2743" "BC-AANGRENZENDE CONSTRUCTIE_METSELWERK" 7 0.18 "CONTINUOUS" "2740" "G/A")
  (list "2741" "BC-AANGRENZENDE CONSTRUCTIE_STAAL" 7 0.18 "CONTINUOUS" "2740" "G/A")
  (list "2712" "BC-BETONVORM" 50 0.18 "CONTINUOUS" "" "G/A")
  (list "2729" "BC-WAPENING_BIJLEGWAPENING" 150 0.18 "CONTINUOUS" "2727" "G")
  (list "2731" "BC-WAPENING_LOOPLIJN" 10 0.18 "CONTINUOUS" "2727" "G")
  (list "2728" "BC-WAPENING_HOOFDWAPENING" 170 0.18 "CONTINUOUS" "2727" "G")
  (list "2730" "BC-WAPENING_SUPPORT" 7 0.18 "CONTINUOUS" "2727" "G")
  (list "2715" "BC-BETONVORM_VSP" 50 0.18 "CONTINUOUS" "2712" "G")
  (list "2718" "BC-BETONVORM_GEWAPEND" 50 0.18 "CONTINUOUS" "2712" "G")
  (list "2713" "BC-BETONVORM_LICHT" 50 0.18 "CONTINUOUS" "2712" "G")
  (list "2714" "BC-BETONVORM_PREFAB" 50 0.18 "CONTINUOUS" "2712" "G")
  (list "2720" "BC-BETONVORM_BALLAST" 50 0.18 "CONTINUOUS" "2712" "G")
  (list "2717" "BC-BETONVORM_OWB" 50 0.18 "CONTINUOUS" "2712" "G")
  (list "2719" "BC-BETONVORM_ONGEWAPEND" 50 0.18 "CONTINUOUS" "2712" "G")
  (list "2721" "BC-BETONVORM_WERKVLOER" 10 0.18 "CONTINUOUS" "2712" "G")
  (list "2880" "BC-BETONVORM_IN HET WERK GESTORT" 50 0.18 "CONTINUOUS" "2712" "G")
  (list "2739" "BC-VOORSPANNING_SUPPORT" 7 0.18 "CONTINUOUS" "2732" "G")
  (list "2733" "BC-VOORSPANNING_ZONDER AANHECHTING" 180 0.18 "CONTINUOUS" "2732" "G")
  (list "2736" "BC-VOORSPANNING_MET AANHECHTING" 180 0.18 "CONTINUOUS" "2732" "G")
  (list "2716" "BC-BETONVORM_VSP_PREFAB" 50 0.18 "CONTINUOUS" "2715" "G")
  (list "2735" "BC-VOORSPANNING_ZONDER AANHECHTING_VERANKERING" 180 0.18 "CONTINUOUS" "2733" "G")
  (list "2734" "BC-VOORSPANNING_ZONDER AANHECHTING_KABEL" 180 0.18 "CONTINUOUS" "2733" "G")
  (list "2737" "BC-VOORSPANNING_MET AANHECHTING_KABEL" 180 0.18 "BC-KABEL-SO" "2736" "G")
  (list "2738" "BC-VOORSPANNING_MET AANHECHTING_VERANKERING" 180 0.18 "CONTINUOUS" "2736" "G")
  (list "2740" "BC-AANGRENZENDE CONSTRUCTIE" 7 0.18 "CONTINUOUS" "" "G")
  (list "2726" "BC-OPLEGBLOK" 30 0.18 "CONTINUOUS" "" "G")
  (list "2746" "BC-LEVENSDUURVERLENGENDE MAATREGEL" 170 0.18 "CONTINUOUS" "" "G")
  (list "2723" "BC-SLOOPLIJN" 10 0.18 "BC-SLOOPLIJN-SO" "" "G")
  (list "2722" "BC-STORTNAAD" 10 0.18 "BC-STORTNAAD-SO" "" "G")
  (list "2745" "BC-REPARATIES" 170 0.18 "CONTINUOUS" "" "G")
  (list "2725" "BC-ITSO" 30 0.18 "CONTINUOUS" "" "G")
  (list "3009" "BC-DILATATIE" 7 0.18 "CONTINUOUS" "" "G")
  (list "2744" "BC-OVERIGMATERIAAL" 7 0.18 "CONTINUOUS" "" "G")
  (list "2724" "BC-VOEGPROFIEL" 30 0.18 "CONTINUOUS" "" "G")
)) *nlcs-layers*))

; Bermbeveiliging (BV) - 84 lagen
(setq *nlcs-layers* (cons (list "BV" "Bermbeveiliging" (list
  (list "3487" "BV-GELEIDECONSTRUCTIE_GELEIDERAIL_KOPPELING_SCHILDMUUR" 20 0.18 "CONTINUOUS" "220" "G/S")
  (list "233" "BV-LEUNING" 210 0.18 "BV-LEUNING-SO" "" "G/S")
  (list "151" "BV-GELEIDECONSTRUCTIE" 210 0.18 "CONTINUOUS" "" "G/S")
  (list "227" "BV-GELEIDECONSTRUCTIE_BEBAKENING" 210 0.18 "CONTINUOUS" "151" "G")
  (list "168" "BV-GELEIDECONSTRUCTIE_GELEIDERAIL" 210 0.18 "BV-GELEIDERAIL-SO" "151" "G")
  (list "152" "BV-GELEIDECONSTRUCTIE_GELEIDEBARRIER" 210 0.18 "BV-GELEIDEBARRIER-SO" "151" "G")
  (list "229" "BV-OBSTAKELBEVEILIGER_RIMOB" 210 0.18 "CONTINUOUS" "228" "G")
  (list "206" "BV-GELEIDECONSTRUCTIE_GELEIDERAIL_OVERGANG" 210 0.18 "CONTINUOUS" "168" "G")
  (list "189" "BV-GELEIDECONSTRUCTIE_GELEIDERAIL_KUNSTWERK" 210 0.18 "BV-GELEIDERAIL_K-SO" "168" "G")
  (list "221" "BV-GELEIDECONSTRUCTIE_GELEIDERAIL_VERANKERING" 210 0.18 "CONTINUOUS" "168" "G")
  (list "215" "BV-GELEIDECONSTRUCTIE_GELEIDERAIL_ANTIVERBLINDINGSSCHERM" 210 0.18 "CONTINUOUS" "168" "G")
  (list "220" "BV-GELEIDECONSTRUCTIE_GELEIDERAIL_KOPPELING" 210 0.18 "CONTINUOUS" "168" "G")
  (list "212" "BV-GELEIDECONSTRUCTIE_GELEIDERAIL_OVERSTAPCONSTRUCTIE" 210 0.18 "CONTINUOUS" "168" "G")
  (list "169" "BV-GELEIDECONSTRUCTIE_GELEIDERAIL_AARDENBAAN" 210 0.18 "BV-GELEIDERAIL_A-SO" "168" "G")
  (list "219" "BV-GELEIDECONSTRUCTIE_GELEIDERAIL_DOORGANG" 210 0.18 "CONTINUOUS" "168" "G")
  (list "153" "BV-GELEIDECONSTRUCTIE_GELEIDEBARRIER_STEPBARRIER" 210 0.18 "BV-STEPBARRIER-SO" "152" "G")
  (list "166" "BV-GELEIDECONSTRUCTIE_GELEIDEBARRIER_OVERSTAPCONSTRUCTIE" 210 0.18 "CONTINUOUS" "152" "G")
  (list "165" "BV-GELEIDECONSTRUCTIE_GELEIDEBARRIER_OVERGANG" 210 0.18 "CONTINUOUS" "152" "G")
  (list "167" "BV-GELEIDECONSTRUCTIE_GELEIDEBARRIER_ANTIVERBLINDINGSSCHERM" 210 0.18 "CONTINUOUS" "152" "G")
  (list "230" "BV-OBSTAKELBEVEILIGER_RIMOB_V270" 210 0.18 "CONTINUOUS" "229" "G")
  (list "232" "BV-OBSTAKELBEVEILIGER_RIMOB_P110" 210 0.18 "CONTINUOUS" "229" "G")
  (list "231" "BV-OBSTAKELBEVEILIGER_RIMOB_V185" 210 0.18 "CONTINUOUS" "229" "G")
  (list "210" "BV-GELEIDECONSTRUCTIE_GELEIDERAIL_OVERGANG_SCHUIFVERBINDING" 210 0.18 "CONTINUOUS" "206" "G")
  (list "207" "BV-GELEIDECONSTRUCTIE_GELEIDERAIL_OVERGANG_6080" 210 0.18 "CONTINUOUS" "206" "G")
  (list "211" "BV-GELEIDECONSTRUCTIE_GELEIDERAIL_OVERGANG_PASPLANK" 210 0.18 "CONTINUOUS" "206" "G")
  (list "208" "BV-GELEIDECONSTRUCTIE_GELEIDERAIL_OVERGANG_8060" 210 0.18 "CONTINUOUS" "206" "G")
  (list "209" "BV-GELEIDECONSTRUCTIE_GELEIDERAIL_OVERGANG_SPLITSING" 210 0.18 "CONTINUOUS" "206" "G")
  (list "203" "BV-GELEIDECONSTRUCTIE_GELEIDERAIL_KUNSTWERK_VLP1R13360" 210 0.18 "BV-VLP1R13360-SO" "189" "G")
  (list "200" "BV-GELEIDECONSTRUCTIE_GELEIDERAIL_KUNSTWERK_VLP1LV13360" 210 0.18 "BV-VLP1LV13360-SO" "189" "G")
  (list "197" "BV-GELEIDECONSTRUCTIE_GELEIDERAIL_KUNSTWERK_VLP1DL13360" 210 0.18 "BV-VLP1DL13360-SO" "189" "G")
  (list "190" "BV-GELEIDECONSTRUCTIE_GELEIDERAIL_KUNSTWERK_F2DL40080" 210 0.18 "BV-F2DL40080-SO" "189" "G")
  (list "225" "BV-GELEIDECONSTRUCTIE_GELEIDERAIL_VERANKERING_KORTLINKS" 210 0.18 "CONTINUOUS" "221" "G")
  (list "226" "BV-GELEIDECONSTRUCTIE_GELEIDERAIL_VERANKERING_BOVENGRONDS" 210 0.18 "CONTINUOUS" "221" "G")
  (list "222" "BV-GELEIDECONSTRUCTIE_GELEIDERAIL_VERANKERING_RECHTS" 210 0.18 "CONTINUOUS" "221" "G")
  (list "224" "BV-GELEIDECONSTRUCTIE_GELEIDERAIL_VERANKERING_LINKS" 210 0.18 "CONTINUOUS" "221" "G")
  (list "223" "BV-GELEIDECONSTRUCTIE_GELEIDERAIL_VERANKERING_KORTRECHTS" 210 0.18 "CONTINUOUS" "221" "G")
  (list "217" "BV-GELEIDECONSTRUCTIE_GELEIDERAIL_ANTIVERBLINDINGSSCHERM_SCHERM" 210 0.18 "BV-ANTIVERBLINDINGSSCHERM-SO" "215" "G")
  (list "216" "BV-GELEIDECONSTRUCTIE_GELEIDERAIL_ANTIVERBLINDINGSSCHERM_LAMELLEN" 210 0.18 "BV-ANTIVERBLINDINGSSCHERM-SO" "215" "G")
  (list "218" "BV-GELEIDECONSTRUCTIE_GELEIDERAIL_ANTIVERBLINDINGSSCHERM_FLEXLAMELLEN" 210 0.18 "BV-ANTIVERBLINDINGSSCHERM-SO" "215" "G")
  (list "213" "BV-GELEIDECONSTRUCTIE_GELEIDERAIL_OVERSTAPCONSTRUCTIE_600" 210 0.18 "CONTINUOUS" "212" "G")
  (list "214" "BV-GELEIDECONSTRUCTIE_GELEIDERAIL_OVERSTAPCONSTRUCTIE_800" 210 0.18 "CONTINUOUS" "212" "G")
  (list "171" "BV-GELEIDECONSTRUCTIE_GELEIDERAIL_AARDENBAAN_VLP2Z26780" 210 0.18 "BV-VLP2Z26780-SO" "169" "G")
  (list "183" "BV-GELEIDECONSTRUCTIE_GELEIDERAIL_AARDENBAAN_VLP1Z13360" 210 0.18 "BV-VLP1Z13360-SO" "169" "G")
  (list "180" "BV-GELEIDECONSTRUCTIE_GELEIDERAIL_AARDENBAAN_VLP1Z26760" 210 0.18 "BV-VLP1Z26760-SO" "169" "G")
  (list "186" "BV-GELEIDECONSTRUCTIE_GELEIDERAIL_AARDENBAAN_VLP1ZC13360" 210 0.18 "BV-VLP1ZC13360-SO" "169" "G")
  (list "177" "BV-GELEIDECONSTRUCTIE_GELEIDERAIL_AARDENBAAN_VLP2ZC13380" 210 0.18 "BV-VLP2ZC13380-SO" "169" "G")
  (list "174" "BV-GELEIDECONSTRUCTIE_GELEIDERAIL_AARDENBAAN_VLP2Z13380" 210 0.18 "BV-VLP2Z13380-SO" "169" "G")
  (list "170" "BV-GELEIDECONSTRUCTIE_GELEIDERAIL_AARDENBAAN_F2M40080" 210 0.18 "BV-F2M40080-SO" "169" "G")
  (list "155" "BV-GELEIDECONSTRUCTIE_GELEIDEBARRIER_STEPBARRIER_BETON" 210 0.18 "BV-STEPBARRIER_B-SO" "153" "G")
  (list "154" "BV-GELEIDECONSTRUCTIE_GELEIDEBARRIER_STEPBARRIER_STAALVERANKERD" 210 0.18 "BV-STEPBARRIER_S-SO" "153" "G")
  (list "204" "BV-GELEIDECONSTRUCTIE_GELEIDERAIL_KUNSTWERK_VLP1R13360_LINKS" 210 0.18 "BV-VLP1R13360-SO" "203" "G")
  (list "205" "BV-GELEIDECONSTRUCTIE_GELEIDERAIL_KUNSTWERK_VLP1R13360_RECHTS" 210 0.18 "BV-VLP1R13360-SO" "203" "G")
  (list "201" "BV-GELEIDECONSTRUCTIE_GELEIDERAIL_KUNSTWERK_VLP1LV13360_LINKS" 210 0.18 "BV-VLP1LV13360-SO" "200" "G")
  (list "202" "BV-GELEIDECONSTRUCTIE_GELEIDERAIL_KUNSTWERK_VLP1LV13360_RECHTS" 210 0.18 "BV-VLP1LV13360-SO" "200" "G")
  (list "199" "BV-GELEIDECONSTRUCTIE_GELEIDERAIL_KUNSTWERK_VLP1DL13360_RECHTS" 210 0.18 "BV-VLP1DL13360-SO" "197" "G")
  (list "198" "BV-GELEIDECONSTRUCTIE_GELEIDERAIL_KUNSTWERK_VLP1DL13360_LINKS" 210 0.18 "BV-VLP1DL13360-SO" "197" "G")
  (list "173" "BV-GELEIDECONSTRUCTIE_GELEIDERAIL_AARDENBAAN_VLP2Z26780_RECHTS" 210 0.18 "BV-VLP2Z26780-SO" "171" "G")
  (list "172" "BV-GELEIDECONSTRUCTIE_GELEIDERAIL_AARDENBAAN_VLP2Z26780_LINKS" 210 0.18 "BV-VLP2Z26780-SO" "171" "G")
  (list "184" "BV-GELEIDECONSTRUCTIE_GELEIDERAIL_AARDENBAAN_VLP1Z13360_LINKS" 210 0.18 "BV-VLP1Z13360-SO" "183" "G")
  (list "185" "BV-GELEIDECONSTRUCTIE_GELEIDERAIL_AARDENBAAN_VLP1Z13360_RECHTS" 210 0.18 "BV-VLP1Z13360-SO" "183" "G")
  (list "181" "BV-GELEIDECONSTRUCTIE_GELEIDERAIL_AARDENBAAN_VLP1Z26760_LINKS" 210 0.18 "BV-VLP1Z26760-SO" "180" "G")
  (list "182" "BV-GELEIDECONSTRUCTIE_GELEIDERAIL_AARDENBAAN_VLP1Z26760_RECHTS" 210 0.18 "BV-VLP1Z26760-SO" "180" "G")
  (list "187" "BV-GELEIDECONSTRUCTIE_GELEIDERAIL_AARDENBAAN_VLP1ZC13360_LINKS" 210 0.18 "BV-VLP1ZC13360-SO" "186" "G")
  (list "188" "BV-GELEIDECONSTRUCTIE_GELEIDERAIL_AARDENBAAN_VLP1ZC13360_RECHTS" 210 0.18 "BV-VLP1ZC13360-SO" "186" "G")
  (list "179" "BV-GELEIDECONSTRUCTIE_GELEIDERAIL_AARDENBAAN_VLP2ZC13380_RECHTS" 210 0.18 "BV-VLP2ZC13380-SO" "177" "G")
  (list "178" "BV-GELEIDECONSTRUCTIE_GELEIDERAIL_AARDENBAAN_VLP2ZC13380_LINKS" 210 0.18 "BV-VLP2ZC13380-SO" "177" "G")
  (list "175" "BV-GELEIDECONSTRUCTIE_GELEIDERAIL_AARDENBAAN_VLP2Z13380_LINKS" 210 0.18 "BV-VLP2Z13380-SO" "174" "G")
  (list "176" "BV-GELEIDECONSTRUCTIE_GELEIDERAIL_AARDENBAAN_VLP2Z13380_RECHTS" 210 0.18 "BV-VLP2Z13380-SO" "174" "G")
  (list "156" "BV-GELEIDECONSTRUCTIE_GELEIDEBARRIER_STEPBARRIER_BETON_PREFABVERANKERD" 210 0.18 "BV-STEPBARRIER_BV-SO" "155" "G")
  (list "157" "BV-GELEIDECONSTRUCTIE_GELEIDEBARRIER_STEPBARRIER_BETON_PREFABGEKOPPELD" 210 0.18 "BV-STEPBARRIER_BG-SO" "155" "G")
  (list "158" "BV-GELEIDECONSTRUCTIE_GELEIDEBARRIER_STEPBARRIER_BETON_SLIPFORMPAVER" 210 0.18 "BV-SLIPFORM-SO" "155" "G")
  (list "228" "BV-OBSTAKELBEVEILIGER" 210 0.18 "CONTINUOUS" "" "G")
  (list "191" "BV-GELEIDECONSTRUCTIE_GELEIDERAIL_KUNSTWERK_VLP2DL13380" 210 0.18 "BV-VLP2DL13380-SO" "189" "G")
  (list "194" "BV-GELEIDECONSTRUCTIE_GELEIDERAIL_KUNSTWERK_VLP2R13380" 210 0.18 "BV-VLP2R13380-SO" "189" "G")
  (list "159" "BV-GELEIDECONSTRUCTIE_GELEIDEBARRIER_STEPBARRIER_RWS" 7 0.25 "CONTINUOUS" "153" "G")
  (list "162" "BV-GELEIDECONSTRUCTIE_GELEIDEBARRIER_STEPBARRIER_VARIOGUARD" 7 0.25 "CONTINUOUS" "153" "G")
  (list "163" "BV-GELEIDECONSTRUCTIE_GELEIDEBARRIER_STEPBARRIER_A1" 7 0.25 "CONTINUOUS" "153" "G")
  (list "161" "BV-GELEIDECONSTRUCTIE_GELEIDEBARRIER_STEPBARRIER_VECUSEC" 7 0.25 "CONTINUOUS" "153" "G")
  (list "160" "BV-GELEIDECONSTRUCTIE_GELEIDEBARRIER_STEPBARRIER_SAFEGUARD" 7 0.25 "CONTINUOUS" "153" "G")
  (list "164" "BV-GELEIDECONSTRUCTIE_GELEIDEBARRIER_STEPBARRIER_BEVER" 7 0.25 "CONTINUOUS" "153" "G")
  (list "192" "BV-GELEIDECONSTRUCTIE_GELEIDERAIL_KUNSTWERK_VLP2DL13380_LINKS" 210 0.18 "BV-VLP2DL13380-SO" "191" "G")
  (list "193" "BV-GELEIDECONSTRUCTIE_GELEIDERAIL_KUNSTWERK_VLP2DL13380_RECHTS" 210 0.18 "BV-VLP2DL13380-SO" "191" "G")
  (list "195" "BV-GELEIDECONSTRUCTIE_GELEIDERAIL_KUNSTWERK_VLP2R13380_LINKS" 210 0.18 "BV-VLP2R13380-SO" "194" "G")
  (list "196" "BV-GELEIDECONSTRUCTIE_GELEIDERAIL_KUNSTWERK_VLP2R13380_RECHTS" 210 0.18 "BV-VLP2R13380-SO" "194" "G")
)) *nlcs-layers*))

; Funderingsconstructies (FC) - 22 lagen
(setq *nlcs-layers* (cons (list "FC" "Funderingsconstructies" (list
  (list "2755" "FC-PAAL_STAALBUIS" 140 0.18 "CONTINUOUS" "2747" "G/S")
  (list "2750" "FC-PAAL_BETON" 50 0.18 "CONTINUOUS" "2747" "G/S/A")
  (list "2748" "FC-PAAL_HOUT" 30 0.18 "CONTINUOUS" "2747" "G/A/S")
  (list "2766" "FC-KESP" 60 0.18 "CONTINUOUS" "" "G/S/A")
  (list "2761" "FC-DAMWAND_BETON" 50 0.18 "CONTINUOUS" "2758" "G/A")
  (list "2762" "FC-DAMWAND_ANKER" 60 0.18 "CONTINUOUS" "2758" "G/A")
  (list "2759" "FC-DAMWAND_HOUT" 30 0.18 "CONTINUOUS" "2758" "G/A")
  (list "2760" "FC-DAMWAND_STAAL" 140 0.18 "CONTINUOUS" "2758" "G/A")
  (list "2752" "FC-PAAL_BETON_IN DE GRONDGEVORMD" 50 0.18 "CONTINUOUS" "2750" "G/A")
  (list "2754" "FC-PAAL_BETON_SCHROEFPAAL" 50 0.18 "CONTINUOUS" "2750" "G/A")
  (list "2751" "FC-PAAL_BETON_PREFAB" 50 0.18 "CONTINUOUS" "2750" "G/A")
  (list "2749" "FC-PAAL_HOUT_OPLANGER" 30 0.18 "CONTINUOUS" "2748" "G/A")
  (list "2753" "FC-PAAL_BETON_IN DE GRONDGEVORMD_TREKPAAL" 50 0.18 "CONTINUOUS" "2752" "G/A")
  (list "2763" "FC-DAMWAND_ANKER_GROUT" 60 0.18 "CONTINUOUS" "2762" "G")
  (list "2756" "FC-PAAL_STAALBUIS_SCHROEFPAAL" 140 0.18 "CONTINUOUS" "2755" "G")
  (list "2758" "FC-DAMWAND" 60 0.18 "CONTINUOUS" "" "G")
  (list "2757" "FC-DIEPWAND" 60 0.18 "CONTINUOUS" "" "G")
  (list "2768" "FC-LEVENSDUURVERLENGENDE MAATREGEL" 170 0.18 "CONTINUOUS" "" "G")
  (list "2765" "FC-GRONDVERBETERING" 30 0.18 "CONTINUOUS" "" "G")
  (list "2764" "FC-OPSTAAL" 50 0.18 "CONTINUOUS" "" "G")
  (list "2747" "FC-PAAL" 40 0.18 "CONTINUOUS" "" "G")
  (list "2767" "FC-REPARATIES" 170 0.18 "CONTINUOUS" "" "G")
)) *nlcs-layers*))

; Faunavoorzieningen (FV) - 58 lagen
(setq *nlcs-layers* (cons (list "FV" "Faunavoorzieningen" (list
  (list "238" "FV-ECOLOGISCHEVERBINDINGSZONE_CORRIDOR" 80 0.18 "CONTINUOUS" "234" "G")
  (list "235" "FV-ECOLOGISCHEVERBINDINGSZONE_ROBUUST" 80 0.18 "CONTINUOUS" "234" "G")
  (list "241" "FV-ECOLOGISCHEVERBINDINGSZONE_STAPSTEEN" 80 0.18 "CONTINUOUS" "234" "G")
  (list "288" "FV-FAUNAVOORZIENING_LICHTKOKER" 70 0.18 "CONTINUOUS" "278" "G")
  (list "284" "FV-FAUNAVOORZIENING_LOOPPLANK" 70 0.18 "CONTINUOUS" "278" "G")
  (list "279" "FV-FAUNAVOORZIENING_TERUGKEERVOORZIENING" 70 0.18 "CONTINUOUS" "278" "G")
  (list "283" "FV-FAUNAVOORZIENING_GRONDDAM" 70 0.18 "CONTINUOUS" "278" "G")
  (list "287" "FV-FAUNAVOORZIENING_AFSCHERMINGLICHT" 70 0.18 "CONTINUOUS" "278" "G")
  (list "266" "FV-GELEIDING_WILDRASTER" 80 0.18 "CONTINUOUS" "265" "G")
  (list "277" "FV-GELEIDING_STOBBENWAL" 80 0.18 "CONTINUOUS" "265" "G")
  (list "276" "FV-GELEIDING_WILDROOSTER" 80 0.18 "CONTINUOUS" "265" "G")
  (list "259" "FV-NATUURVRIENDELIJKEOEVER_DOORGROEIBARECONSTRUCTIE" 110 0.18 "CONTINUOUS" "258" "G")
  (list "262" "FV-NATUURVRIENDELIJKEOEVER_FLAUWEOEVER" 110 0.18 "CONTINUOUS" "258" "G")
  (list "263" "FV-NATUURVRIENDELIJKEOEVER_PLASDRASBERM" 110 0.18 "CONTINUOUS" "258" "G")
  (list "264" "FV-NATUURVRIENDELIJKEOEVER_VOOROEVERVERDEDIGING" 110 0.18 "CONTINUOUS" "258" "G")
  (list "247" "FV-FAUNAPASSAGE_BRUGDOORLOPENDEOEVER" 90 0.18 "CONTINUOUS" "244" "G")
  (list "255" "FV-FAUNAPASSAGE_BRUGDUIKERMETFAUNAVOORZIENING" 90 0.18 "CONTINUOUS" "244" "G")
  (list "252" "FV-FAUNAPASSAGE_BOOMBRUG" 90 0.18 "CONTINUOUS" "244" "G")
  (list "245" "FV-FAUNAPASSAGE_ECODUCT" 80 0.18 "CONTINUOUS" "244" "G")
  (list "250" "FV-FAUNAPASSAGE_DASSENTUNNEL" 90 0.18 "CONTINUOUS" "244" "G")
  (list "253" "FV-FAUNAPASSAGE_HOPOVER" 90 0.18 "CONTINUOUS" "244" "G")
  (list "251" "FV-FAUNAPASSAGE_AMFIBIEENTUNNEL" 90 0.18 "CONTINUOUS" "244" "G")
  (list "249" "FV-FAUNAPASSAGE_FAUNATUNNEL" 90 0.18 "CONTINUOUS" "244" "G")
  (list "248" "FV-FAUNAPASSAGE_ECODUIKER" 90 0.18 "CONTINUOUS" "244" "G")
  (list "246" "FV-FAUNAPASSAGE_VIADUCT" 90 0.18 "CONTINUOUS" "244" "G")
  (list "2881" "FV-FAUNAPASSAGE_WILDRICHEL" 80 0.18 "CONTINUOUS" "244" "G")
  (list "239" "FV-ECOLOGISCHEVERBINDINGSZONE_CORRIDOR_NAT" 80 0.18 "CONTINUOUS" "238" "G")
  (list "240" "FV-ECOLOGISCHEVERBINDINGSZONE_CORRIDOR_DROOG" 80 0.18 "CONTINUOUS" "238" "G")
  (list "236" "FV-ECOLOGISCHEVERBINDINGSZONE_ROBUUST_NAT" 80 0.18 "CONTINUOUS" "235" "G")
  (list "237" "FV-ECOLOGISCHEVERBINDINGSZONE_ROBUUST_DROOG" 80 0.18 "CONTINUOUS" "235" "G")
  (list "243" "FV-ECOLOGISCHEVERBINDINGSZONE_STAPSTEEN_DROOG" 80 0.18 "CONTINUOUS" "241" "G")
  (list "242" "FV-ECOLOGISCHEVERBINDINGSZONE_STAPSTEEN_NAT" 80 0.18 "CONTINUOUS" "241" "G")
  (list "289" "FV-FAUNAVOORZIENING_LICHTKOKER_OPEN" 70 0.18 "CONTINUOUS" "288" "G")
  (list "290" "FV-FAUNAVOORZIENING_LICHTKOKER_DICHT" 70 0.18 "CONTINUOUS" "288" "G")
  (list "285" "FV-FAUNAVOORZIENING_LOOPPLANK_BETON" 70 0.18 "CONTINUOUS" "284" "G")
  (list "286" "FV-FAUNAVOORZIENING_LOOPPLANK_HOUT" 70 0.18 "CONTINUOUS" "284" "G")
  (list "282" "FV-FAUNAVOORZIENING_TERUGKEERVOORZIENING_DASSENPOORT" 70 0.18 "CONTINUOUS" "279" "G")
  (list "280" "FV-FAUNAVOORZIENING_TERUGKEERVOORZIENING_INSPRINGVOORZIENING" 70 0.18 "CONTINUOUS" "279" "G")
  (list "281" "FV-FAUNAVOORZIENING_TERUGKEERVOORZIENING_UITTREEVOORZIENING" 70 0.18 "CONTINUOUS" "279" "G")
  (list "275" "FV-GELEIDING_WILDRASTER_BOOMMARTER" 80 0.18 "CONTINUOUS" "266" "G")
  (list "267" "FV-GELEIDING_WILDRASTER_EDELHERT" 80 0.18 "CONTINUOUS" "266" "G")
  (list "271" "FV-GELEIDING_WILDRASTER_AMFIBIE" 80 0.18 "CONTINUOUS" "266" "G")
  (list "269" "FV-GELEIDING_WILDRASTER_WILDZWIJN" 80 0.18 "CONTINUOUS" "266" "G")
  (list "270" "FV-GELEIDING_WILDRASTER_DAS" 80 0.18 "CONTINUOUS" "266" "G")
  (list "274" "FV-GELEIDING_WILDRASTER_KLEINEZOOGDIEREN" 80 0.18 "CONTINUOUS" "266" "G")
  (list "268" "FV-GELEIDING_WILDRASTER_REE" 80 0.18 "CONTINUOUS" "266" "G")
  (list "261" "FV-NATUURVRIENDELIJKEOEVER_DOORGROEIBARECONSTRUCTIE_STORTSTEEN" 110 0.18 "CONTINUOUS" "259" "G")
  (list "260" "FV-NATUURVRIENDELIJKEOEVER_DOORGROEIBARECONSTRUCTIE_SCHANSKORVEN" 110 0.18 "CONTINUOUS" "259" "G")
  (list "256" "FV-FAUNAPASSAGE_BRUGDUIKERMETFAUNAVOORZIENING_LOOPPLANK" 90 0.18 "CONTINUOUS" "255" "G")
  (list "257" "FV-FAUNAPASSAGE_BRUGDUIKERMETFAUNAVOORZIENING_FLORAROL" 90 0.18 "CONTINUOUS" "255" "G")
  (list "272" "FV-GELEIDING_WILDRASTER_AMFIBIE_ROND" 80 0.18 "CONTINUOUS" "271" "G")
  (list "273" "FV-GELEIDING_WILDRASTER_AMFIBIE_VIERKANT" 80 0.18 "CONTINUOUS" "271" "G")
  (list "234" "FV-ECOLOGISCHEVERBINDINGSZONE" 80 0.18 "CONTINUOUS" "" "G")
  (list "278" "FV-FAUNAVOORZIENING" 70 0.18 "CONTINUOUS" "" "G")
  (list "265" "FV-GELEIDING" 80 0.18 "CONTINUOUS" "" "G")
  (list "258" "FV-NATUURVRIENDELIJKEOEVER" 110 0.18 "CONTINUOUS" "" "G")
  (list "254" "FV-FAUNAPASSAGE_VISTRAP" 90 0.18 "CONTINUOUS" "244" "G")
  (list "244" "FV-FAUNAPASSAGE" 80 0.18 "CONTINUOUS" "" "G")
)) *nlcs-layers*))

; Grondkerende constructies (GC) - 28 lagen
(setq *nlcs-layers* (cons (list "GC" "Grondkerende constructies" (list
  (list "2770" "GC-DAMWAND_STAAL" 140 0.18 "CONTINUOUS" "2769" "G/A/S")
  (list "2779" "GC-VERANKERING_ANKERSCHOT" 50 0.18 "CONTINUOUS" "2777" "G/A")
  (list "2778" "GC-VERANKERING_ANKERSTANG" 50 0.18 "CONTINUOUS" "2777" "G/A")
  (list "2780" "GC-VERANKERING_ANKERSCHERM" 50 0.18 "CONTINUOUS" "2777" "G/A")
  (list "2775" "GC-GORDING_HOUT" 30 0.18 "CONTINUOUS" "2773" "G/A")
  (list "2776" "GC-GORDING_BETON" 50 0.18 "CONTINUOUS" "2773" "G/A")
  (list "2774" "GC-GORDING_STAAL" 140 0.18 "CONTINUOUS" "2773" "G/A")
  (list "2788" "GC-DEKSLOOF_BETON" 50 0.18 "CONTINUOUS" "2785" "G/A")
  (list "2786" "GC-DEKSLOOF_STAAL" 140 0.18 "CONTINUOUS" "2785" "G/A")
  (list "2787" "GC-DEKSLOOF_HOUT" 30 0.18 "CONTINUOUS" "2785" "G/A")
  (list "2772" "GC-DAMWAND_BETON" 50 0.18 "CONTINUOUS" "2769" "G/A")
  (list "2771" "GC-DAMWAND_HOUT" 30 0.18 "CONTINUOUS" "2769" "G/A")
  (list "2783" "GC-VERANKERING_KLAPANKER" 50 0.18 "CONTINUOUS" "2777" "G")
  (list "2782" "GC-VERANKERING_SCHROEFANKER" 50 0.18 "CONTINUOUS" "2777" "G")
  (list "2781" "GC-VERANKERING_GROUTANKER" 50 0.18 "CONTINUOUS" "2777" "G")
  (list "2784" "GC-VERANKERING_TREKPAAL" 50 0.18 "CONTINUOUS" "2777" "G")
  (list "2792" "GC-STEMPEL_ONDERWATERBETON" 130 0.18 "CONTINUOUS" "2789" "G")
  (list "2790" "GC-STEMPEL_STAAL" 130 0.18 "CONTINUOUS" "2789" "G")
  (list "2791" "GC-STEMPEL_GROUT" 130 0.18 "CONTINUOUS" "2789" "G")
  (list "2793" "GC-FOLIE" 7 0.18 "CONTINUOUS" "" "")
  (list "2777" "GC-VERANKERING" 50 0.18 "CONTINUOUS" "" "")
  (list "2773" "GC-GORDING" 150 0.18 "CONTINUOUS" "" "")
  (list "2789" "GC-STEMPEL" 130 0.18 "CONTINUOUS" "" "")
  (list "2795" "GC-REPARATIES" 170 0.18 "CONTINUOUS" "" "")
  (list "2785" "GC-DEKSLOOF" 40 0.18 "CONTINUOUS" "" "")
  (list "2796" "GC-LEVENSDUURVERLENGENDE MAATREGEL" 170 0.18 "CONTINUOUS" "" "")
  (list "2769" "GC-DAMWAND" 60 0.18 "CONTINUOUS" "" "")
  (list "2794" "GC-DIEPWAND" 60 0.18 "CONTINUOUS" "" "")
)) *nlcs-layers*))

; Grondkeringen (GK) - 61 lagen
(setq *nlcs-layers* (cons (list "GK" "Grondkeringen" (list
  (list "337" "GK-KISTDAM_TWAND" 40 0.18 "CONTINUOUS" "329" "G")
  (list "330" "GK-KISTDAM_DAMWAND" 40 0.18 "CONTINUOUS" "329" "G")
  (list "338" "GK-KISTDAM_BERLINER WAND" 40 0.18 "CONTINUOUS" "329" "G")
  (list "336" "GK-KISTDAM_LWAND" 40 0.18 "CONTINUOUS" "329" "G")
  (list "335" "GK-KISTDAM_COMBIWAND" 40 0.18 "CONTINUOUS" "329" "G")
  (list "316" "GK-KEERWAND_DAMWAND" 30 0.18 "CONTINUOUS" "315" "G")
  (list "321" "GK-KEERWAND_COMBIWAND" 30 0.18 "CONTINUOUS" "315" "G")
  (list "326" "GK-KEERWAND_TWAND" 30 0.18 "CONTINUOUS" "315" "G")
  (list "328" "GK-KEERWAND_BERLINER WAND" 30 0.18 "CONTINUOUS" "315" "G")
  (list "325" "GK-KEERWAND_LWAND" 30 0.18 "CONTINUOUS" "315" "G")
  (list "324" "GK-KEERWAND_SCHANSKORF" 30 0.18 "CONTINUOUS" "315" "G")
  (list "323" "GK-KEERWAND_TERRE ARMEE" 30 0.18 "CONTINUOUS" "315" "G")
  (list "322" "GK-KEERWAND_DIEPWAND" 30 0.18 "CONTINUOUS" "315" "G")
  (list "340" "GK-BESCHOEIING_DAMWAND" 130 0.18 "GK-BESCHOEIING-SO" "339" "G")
  (list "348" "GK-BESCHOEIING_BETON" 130 0.18 "GK-BESCHOEIING-SO" "339" "G")
  (list "352" "GK-BESCHOEIING_NATUURVRIENDELIJK" 90 0.18 "CONTINUOUS" "339" "G")
  (list "345" "GK-BESCHOEIING_HOUT" 130 0.18 "GK-BESCHOEIING-SO" "339" "G")
  (list "350" "GK-BESCHOEIING_KUNSTSTOF" 130 0.18 "GK-BESCHOEIING-SO" "339" "G")
  (list "349" "GK-BESCHOEIING_STAAL" 130 0.18 "GK-BESCHOEIING-SO" "339" "G")
  (list "314" "GK-BOUWKUIP_DIEPWAND" 210 0.18 "CONTINUOUS" "307" "G")
  (list "308" "GK-BOUWKUIP_DAMWAND" 210 0.18 "CONTINUOUS" "307" "G")
  (list "313" "GK-BOUWKUIP_COMBIWAND" 210 0.18 "CONTINUOUS" "307" "G")
  (list "304" "GK-KADEMUUR_OVERBOUWD TALUD" 150 0.18 "CONTINUOUS" "291" "G")
  (list "301" "GK-KADEMUUR_ONTLASTVLOER" 150 0.18 "CONTINUOUS" "291" "G")
  (list "292" "GK-KADEMUUR_GEWICHTSCONSTRUCTIE" 150 0.18 "CONTINUOUS" "291" "G")
  (list "298" "GK-KADEMUUR_WANDCONSTRUCTIE" 150 0.18 "CONTINUOUS" "291" "G")
  (list "333" "GK-KISTDAM_DAMWAND_BETON" 40 0.18 "CONTINUOUS" "330" "G")
  (list "331" "GK-KISTDAM_DAMWAND_STAAL" 40 0.18 "CONTINUOUS" "330" "G")
  (list "332" "GK-KISTDAM_DAMWAND_HOUT" 40 0.18 "CONTINUOUS" "330" "G")
  (list "334" "GK-KISTDAM_DAMWAND_KUNSTSTOF" 40 0.18 "CONTINUOUS" "330" "G")
  (list "319" "GK-KEERWAND_DAMWAND_BETON" 30 0.18 "CONTINUOUS" "316" "G")
  (list "320" "GK-KEERWAND_DAMWAND_KUNSTSTOF" 30 0.18 "CONTINUOUS" "316" "G")
  (list "318" "GK-KEERWAND_DAMWAND_HOUT" 30 0.18 "CONTINUOUS" "316" "G")
  (list "317" "GK-KEERWAND_DAMWAND_STAAL" 30 0.18 "CONTINUOUS" "316" "G")
  (list "343" "GK-BESCHOEIING_DAMWAND_BETON" 130 0.18 "GK-BESCHOEIING-SO" "340" "G")
  (list "344" "GK-BESCHOEIING_DAMWAND_KUNSTSTOF" 130 0.18 "GK-BESCHOEIING-SO" "340" "G")
  (list "341" "GK-BESCHOEIING_DAMWAND_STAAL" 130 0.18 "GK-BESCHOEIING-SO" "340" "G")
  (list "342" "GK-BESCHOEIING_DAMWAND_HOUT" 130 0.18 "GK-BESCHOEIING-SO" "340" "G")
  (list "347" "GK-BESCHOEIING_HOUT_PERKOENPALENRIJ" 130 0.18 "GK-PERKOEN-SO" "345" "G")
  (list "346" "GK-BESCHOEIING_HOUT_SCHOT" 130 0.18 "GK-BESCHOEIING-SO" "345" "G")
  (list "351" "GK-BESCHOEIING_KUNSTSTOF_SCHOT" 130 0.18 "GK-BESCHOEIING-SO" "350" "G")
  (list "312" "GK-BOUWKUIP_DAMWAND_KUNSTSTOF" 210 0.18 "CONTINUOUS" "308" "G")
  (list "310" "GK-BOUWKUIP_DAMWAND_HOUT" 210 0.18 "CONTINUOUS" "308" "G")
  (list "309" "GK-BOUWKUIP_DAMWAND_STAAL" 210 0.18 "CONTINUOUS" "308" "G")
  (list "311" "GK-BOUWKUIP_DAMWAND_BETON" 210 0.18 "CONTINUOUS" "308" "G")
  (list "305" "GK-KADEMUUR_OVERBOUWD TALUD_DEK OVER GLOOIINGSCONSTRUCTIE" 150 0.18 "CONTINUOUS" "304" "G")
  (list "306" "GK-KADEMUUR_OVERBOUWD TALUD_MET KERENDE WAND" 150 0.18 "CONTINUOUS" "304" "G")
  (list "302" "GK-KADEMUUR_ONTLASTVLOER_HOOGGELEGEN" 150 0.18 "CONTINUOUS" "301" "G")
  (list "303" "GK-KADEMUUR_ONTLASTVLOER_DIEPGELEGEN" 150 0.18 "CONTINUOUS" "301" "G")
  (list "296" "GK-KADEMUUR_GEWICHTSCONSTRUCTIE_CELLENWAND" 150 0.18 "CONTINUOUS" "292" "G")
  (list "293" "GK-KADEMUUR_GEWICHTSCONSTRUCTIE_BLOKKENMUUR" 150 0.18 "CONTINUOUS" "292" "G")
  (list "294" "GK-KADEMUUR_GEWICHTSCONSTRUCTIE_L MUUR" 150 0.18 "CONTINUOUS" "292" "G")
  (list "295" "GK-KADEMUUR_GEWICHTSCONSTRUCTIE_CAISSONWAND" 150 0.18 "CONTINUOUS" "292" "G")
  (list "297" "GK-KADEMUUR_GEWICHTSCONSTRUCTIE_TERRE ARMEE" 150 0.18 "CONTINUOUS" "292" "G")
  (list "300" "GK-KADEMUUR_WANDCONSTRUCTIE_VERANKERD" 150 0.18 "CONTINUOUS" "298" "G")
  (list "299" "GK-KADEMUUR_WANDCONSTRUCTIE_ONVERANKERD" 150 0.18 "CONTINUOUS" "298" "G")
  (list "329" "GK-KISTDAM" 40 0.18 "CONTINUOUS" "" "G")
  (list "339" "GK-BESCHOEIING" 130 0.18 "GK-BESCHOEIING-SO" "" "G")
  (list "307" "GK-BOUWKUIP" 210 0.18 "CONTINUOUS" "" "G")
  (list "291" "GK-KADEMUUR" 150 0.18 "CONTINUOUS" "" "G")
  (list "315" "GK-KEERWAND" 30 0.18 "CONTINUOUS" "" "G")
)) *nlcs-layers*))

; Groen (GR) - 99 lagen
(setq *nlcs-layers* (cons (list "GR" "Groen" (list
  (list "3371" "GR-FRUITTEELT_BOOMGAARD" 90 0.13 "CONTINUOUS" "3370" "G/S")
  (list "3367" "GR-DUIN_OPEN VEGETATIE" 40 0.13 "CONTINUOUS" "3366" "G/S")
  (list "3368" "GR-DUIN_GESLOTEN VEGETATIE" 40 0.13 "CONTINUOUS" "3366" "G/S")
  (list "2886" "GR-BEPLANTING_CULTUUR" 90 0.18 "CONTINUOUS" "2885" "G/A/S")
  (list "2896" "GR-BEPLANTING_NATUUR" 90 0.18 "CONTINUOUS" "2885" "G/A/S")
  (list "2892" "GR-BEPLANTING_CULTUUR_WATERPLANT" 90 0.18 "CONTINUOUS" "2886" "G/A/S")
  (list "2894" "GR-BEPLANTING_CULTUUR_WISSELPERK" 90 0.18 "CONTINUOUS" "2886" "G/A/S")
  (list "368" "GR-HOUTOPSTAND" 40 0.13 "CONTINUOUS" "" "G/A/S")
  (list "372" "GR-STRUWEEL" 90 0.13 "CONTINUOUS" "" "G/A/S")
  (list "3377" "GR-BOUWLAND" 80 0.13 "CONTINUOUS" "" "G/S")
  (list "356" "GR-BOS" 40 0.13 "CONTINUOUS" "" "G/A/S")
  (list "399" "GR-GROND" 90 0.13 "CONTINUOUS" "" "G/A/S")
  (list "400" "GR-TEELGROND" 90 0.13 "CONTINUOUS" "" "G/A/S")
  (list "3502" "GR-BLOEMBAK" 80 0.13 "CONTINUOUS" "" "G/S")
  (list "401" "GR-GRAS" 60 0.13 "CONTINUOUS" "" "G/A/S")
  (list "406" "GR-SPORTVELD" 60 0.13 "CONTINUOUS" "" "G/S/A")
  (list "360" "GR-BOOM" 90 0.13 "CONTINUOUS" "" "G/S")
  (list "374" "GR-MAAIVELD" 90 0.13 "CONTINUOUS" "" "G/A/S")
  (list "3376" "GR-BOOMTEELT" 110 0.13 "CONTINUOUS" "" "G/S")
  (list "396" "GR-BOLLEN" 90 0.13 "CONTINUOUS" "" "G/A/S")
  (list "380" "GR-HAAG" 90 0.13 "GR-HAAG1-SO" "" "G/S")
  (list "3370" "GR-FRUITTEELT" 40 0.13 "CONTINUOUS" "" "G/S")
  (list "354" "GR-SOORTAANDUIDING" 7 0.13 "CONTINUOUS" "" "S")
  (list "3366" "GR-DUIN" 40 0.13 "CONTINUOUS" "" "G/S")
  (list "364" "GR-PLANTGATVERBETERING" 90 0.13 "CONTINUOUS" "" "G/A/S")
  (list "384" "GR-HEESTER" 90 0.13 "CONTINUOUS" "" "G/A/S")
  (list "3384" "GR-BOMENRIJ" 80 0.13 "CONTINUOUS" "" "G/S")
  (list "386" "GR-CONIFEER" 90 0.13 "CONTINUOUS" "" "G/S")
  (list "2885" "GR-BEPLANTING" 90 0.18 "CONTINUOUS" "" "G/A/S")
  (list "365" "GR-BOMENGROND" 30 0.13 "CONTINUOUS" "" "G/A/S")
  (list "397" "GR-KRUIDEN" 90 0.13 "CONTINUOUS" "" "G/A/S")
  (list "412" "GR-MOERAS" 120 0.13 "CONTINUOUS" "" "G/A/S")
  (list "3383" "GR-DOORWORTELBARE RUIMTE" 80 0.13 "CONTINUOUS" "" "G/S")
  (list "366" "GR-BOMENZAND" 30 0.13 "CONTINUOUS" "" "G/A/S")
  (list "398" "GR-PLANTENBAK" 90 0.13 "CONTINUOUS" "" "G/S")
  (list "410" "GR-HEIDE" 200 0.13 "CONTINUOUS" "" "G/S")
  (list "3369" "GR-KWELDER" 40 0.13 "CONTINUOUS" "" "G/S")
  (list "3040" "GR-SIERPLANTSOEN" 90 0.18 "CONTINUOUS" "" "G/S")
  (list "353" "GR-TYPEAANDUIDING" 7 0.13 "CONTINUOUS" "" "S")
  (list "367" "GR-HOUTWAL" 40 0.13 "CONTINUOUS" "" "G/S")
  (list "413" "GR-HONDENTOILET" 30 0.13 "CONTINUOUS" "" "G/S")
  (list "2893" "GR-BEPLANTING_CULTUUR_VASTE PLANTENVAK" 90 0.18 "CONTINUOUS" "2886" "G/S/A")
  (list "2890" "GR-BEPLANTING_CULTUUR_ROOS" 90 0.18 "CONTINUOUS" "2886" "G/S")
  (list "2889" "GR-BEPLANTING_CULTUUR_BODEMBEDEKKER" 90 0.18 "CONTINUOUS" "2886" "G/S")
  (list "411" "GR-RIET" 120 0.13 "CONTINUOUS" "" "G/S/A")
  (list "355" "GR-VERWIJDEREN" 10 0.13 "CONTINUOUS" "" "A")
  (list "369" "GR-HOUTOPSTAND_GEMENGD" 40 0.13 "CONTINUOUS" "368" "G")
  (list "370" "GR-HOUTOPSTAND_LOOF" 40 0.13 "CONTINUOUS" "368" "G")
  (list "371" "GR-HOUTOPSTAND_NAALD" 40 0.13 "CONTINUOUS" "368" "G")
  (list "3378" "GR-BOUWLAND_AKKERBOUW" 80 0.13 "CONTINUOUS" "3377" "G")
  (list "3381" "GR-BOUWLAND_BOLLENTEELT" 220 0.13 "CONTINUOUS" "3377" "G")
  (list "3380" "GR-BOUWLAND_VOLLEGRONDTEELT" 40 0.13 "CONTINUOUS" "3377" "G")
  (list "3379" "GR-BOUWLAND_BRAAKLIGGEND" 200 0.13 "CONTINUOUS" "3377" "G")
  (list "359" "GR-BOS_NAALD" 40 0.13 "CONTINUOUS" "356" "G")
  (list "357" "GR-BOS_GEMENGD" 40 0.13 "CONTINUOUS" "356" "G")
  (list "358" "GR-BOS_LOOF" 40 0.13 "CONTINUOUS" "356" "G")
  (list "2902" "GR-GRAS_GRAFVELD" 80 0.18 "CONTINUOUS" "401" "G")
  (list "405" "GR-GRAS_GESTABILISEERD" 60 0.13 "CONTINUOUS" "401" "G")
  (list "2901" "GR-GRAS_NATUURLIJKE OEVER" 80 0.18 "CONTINUOUS" "401" "G")
  (list "403" "GR-GRAS_RUIGGRAS" 60 0.13 "CONTINUOUS" "401" "G")
  (list "404" "GR-GRAS_KUNSTGRAS" 60 0.13 "CONTINUOUS" "401" "G")
  (list "402" "GR-GRAS_GAZON" 60 0.13 "CONTINUOUS" "401" "G")
  (list "2900" "GR-GRAS_BERM" 80 0.18 "CONTINUOUS" "401" "G")
  (list "408" "GR-SPORTVELD_NATUURGRAS" 60 0.13 "CONTINUOUS" "406" "G")
  (list "407" "GR-SPORTVELD_BELIJNING" 7 0.13 "CONTINUOUS" "406" "G")
  (list "409" "GR-SPORTVELD_KUNSTGRAS" 90 0.13 "CONTINUOUS" "406" "G")
  (list "3503" "GR-BOOM_KROON" 90 0.13 "CONTINUOUS" "360" "G")
  (list "3094" "GR-BOOM_RIJ" 90 0.18 "CONTINUOUS" "360" "G")
  (list "2905" "GR-BOOM_KNOT" 80 0.18 "CONTINUOUS" "360" "G")
  (list "2904" "GR-BOOM_LEI" 80 0.18 "CONTINUOUS" "360" "G")
  (list "361" "GR-BOOM_LAANBEPLANTING" 90 0.13 "CONTINUOUS" "360" "G")
  (list "362" "GR-BOOM_INVERHARDING" 90 0.13 "CONTINUOUS" "360" "G")
  (list "2906" "GR-BOOM_GROEP" 80 0.18 "CONTINUOUS" "360" "G")
  (list "363" "GR-BOOM_INVOLLEGROND" 90 0.13 "CONTINUOUS" "360" "G")
  (list "2907" "GR-BOOM_BOSPLANTSOEN" 80 0.18 "CONTINUOUS" "360" "G")
  (list "2903" "GR-BOOM_SOLITAIR" 80 0.18 "CONTINUOUS" "360" "G")
  (list "381" "GR-HAAG_01" 90 0.13 "GR-HAAG1-SO" "380" "G")
  (list "3095" "GR-HAAG_RUW" 90 0.13 "CONTINUOUS" "380" "G")
  (list "382" "GR-HAAG_02" 90 0.13 "GR-HAAG2-SO" "380" "G")
  (list "383" "GR-HAAG_03" 90 0.13 "GR-HAAG3-SO" "380" "G")
  (list "3096" "GR-HAAG_STRAK" 90 0.13 "CONTINUOUS" "380" "G")
  (list "385" "GR-HEESTER_SOLITAIR" 90 0.13 "CONTINUOUS" "384" "G")
  (list "3374" "GR-FRUITTEELT_BOOMGAARD_WIJN" 210 0.13 "CONTINUOUS" "3371" "G")
  (list "3372" "GR-FRUITTEELT_BOOMGAARD_LAAGSTAM" 90 0.13 "CONTINUOUS" "3371" "G")
  (list "3375" "GR-FRUITTEELT_BOOMGAARD_KLEIN FRUIT" 20 0.13 "CONTINUOUS" "3371" "G")
  (list "3373" "GR-FRUITTEELT_BOOMGAARD_HOOGSTAM" 60 0.13 "CONTINUOUS" "3371" "G")
  (list "2895" "GR-BEPLANTING_CULTUUR_BOTANISCHE ROOS" 90 0.18 "CONTINUOUS" "2886" "G")
  (list "2891" "GR-BEPLANTING_CULTUUR_EENJARIGEPLANT" 90 0.18 "CONTINUOUS" "2886" "G")
  (list "2898" "GR-BEPLANTING_NATUUR_BOS" 90 0.18 "CONTINUOUS" "2896" "G")
  (list "2897" "GR-BEPLANTING_NATUUR_BOSPLANTSOEN" 90 0.18 "GR-PLANTSOEN-SO" "2896" "G/A/S")
  (list "2884" "GR-GRIEND" 40 0.18 "CONTINUOUS" "" "G")
  (list "378" "GR-PERK" 90 0.13 "CONTINUOUS" "" "G")
  (list "373" "GR-STRUIK" 90 0.13 "CONTINUOUS" "" "G")
  (list "2883" "GR-HAKHOUT" 40 0.18 "CONTINUOUS" "" "G")
  (list "379" "GR-GROENSTROOK" 90 0.13 "CONTINUOUS" "" "G")
  (list "2899" "GR-GRAS_KRUIDENRIJK" 80 0.18 "CONTINUOUS" "401" "G")
  (list "2888" "GR-BEPLANTING_CULTUUR_HEESTERS" 90 0.18 "CONTINUOUS" "2886" "G")
  (list "2887" "GR-BEPLANTING_CULTUUR_BOSPLANTSOEN" 90 0.18 "GR-PLANTSOEN-SO" "2886" "G/S/A")
  (list "2882" "GR-GROENVOORZIENING" 80 0.18 "CONTINUOUS" "" "G")
)) *nlcs-layers*))

; Grondwerken (GW) - 124 lagen
(setq *nlcs-layers* (cons (list "GW" "Grondwerken" (list
  (list "462" "GW-WATERGANG-WERK" 90 0.18 "CONTINUOUS" "458" "G/A")
  (list "476" "GW-ONTGRAVINGSVAK-WERK" 90 0.18 "CONTINUOUS" "473" "G/A")
  (list "449" "GW-WAL-WERK" 90 0.18 "CONTINUOUS" "446" "G/A")
  (list "445" "GW-OPHOGING-WERK" 90 0.18 "CONTINUOUS" "442" "G/A")
  (list "453" "GW-SLEUF-WERK" 90 0.18 "CONTINUOUS" "450" "G/A")
  (list "457" "GW-CUNET-WERK" 90 0.18 "CONTINUOUS" "454" "G/A")
  (list "467" "GW-WATERGANG_GREPPEL-WERK" 90 0.18 "CONTINUOUS" "463" "G/A")
  (list "472" "GW-WATERGANG_SLOOT-WERK" 90 0.18 "CONTINUOUS" "468" "G/A")
  (list "427" "GW-TALUD" 90 0.18 "CONTINUOUS" "" "")
  (list "516" "GW-BAGGERVAK" 130 0.18 "CONTINUOUS" "" "")
  (list "414" "GW-MAAIVELD" 90 0.18 "GW-MAAIVELD-SO" "" "")
  (list "460" "GW-WATERGANG_INSTEEK" 90 0.18 "CONTINUOUS" "458" "G")
  (list "463" "GW-WATERGANG_GREPPEL" 90 0.18 "CONTINUOUS" "458" "G")
  (list "468" "GW-WATERGANG_SLOOT" 90 0.18 "CONTINUOUS" "458" "G")
  (list "461" "GW-WATERGANG_BODEM" 90 0.18 "CONTINUOUS" "458" "G")
  (list "459" "GW-WATERGANG_WATERLIJN" 150 0.18 "CONTINUOUS" "458" "G")
  (list "4100" "GW-WATERGANG_KNIKLIJN" 90 0.18 "CONTINUOUS" "458" "G")
  (list "4089" "GW-WATERGANG_TALUD" 90 0.18 "CONTINUOUS" "458" "G")
  (list "4099" "GW-WATERGANG_TALUD" 90 0.18 "CONTINUOUS" "458" "G")
  (list "4090" "GW-WATERGANG_KNIKLIJN" 90 0.18 "CONTINUOUS" "458" "G")
  (list "475" "GW-ONTGRAVINGSVAK_BODEM" 90 0.18 "CONTINUOUS" "473" "G")
  (list "474" "GW-ONTGRAVINGSVAK_INSTEEK" 90 0.18 "CONTINUOUS" "473" "G")
  (list "4088" "GW-DIJK_KNIKLIJN" 90 0.18 "CONTINUOUS" "432" "G")
  (list "433" "GW-DIJK_KRUIN" 90 0.18 "CONTINUOUS" "432" "G")
  (list "4097" "GW-DIJK_TALUD" 90 0.18 "CONTINUOUS" "432" "G")
  (list "436" "GW-DIJK_TEEN" 90 0.18 "CONTINUOUS" "432" "G")
  (list "439" "GW-DIJK_BERM" 90 0.18 "CONTINUOUS" "432" "G")
  (list "4098" "GW-DIJK_KNIKLIJN" 90 0.18 "CONTINUOUS" "432" "G")
  (list "4087" "GW-DIJK_TALUD" 90 0.18 "CONTINUOUS" "432" "G")
  (list "429" "GW-TALUD_TEEN" 90 0.18 "CONTINUOUS" "427" "G")
  (list "3008" "GW-TALUD_ONTGRAVING" 90 0.18 "CONTINUOUS" "427" "G")
  (list "3007" "GW-TALUD_AANVULLING" 90 0.18 "CONTINUOUS" "427" "G")
  (list "428" "GW-TALUD_KRUIN" 90 0.18 "CONTINUOUS" "427" "G")
  (list "448" "GW-WAL_TEEN" 90 0.18 "CONTINUOUS" "446" "G")
  (list "447" "GW-WAL_KRUIN" 90 0.18 "CONTINUOUS" "446" "G")
  (list "443" "GW-OPHOGING_KRUIN" 90 0.18 "CONTINUOUS" "442" "G")
  (list "444" "GW-OPHOGING_TEEN" 90 0.18 "CONTINUOUS" "442" "G")
  (list "418" "GW-HOOGTE_GRONDWATERSTAND" 170 0.18 "CONTINUOUS" "416" "G")
  (list "420" "GW-HOOGTE_ZETTING" 7 0.18 "CONTINUOUS" "416" "G")
  (list "419" "GW-HOOGTE_OVERHOOGTE" 7 0.18 "CONTINUOUS" "416" "G")
  (list "417" "GW-HOOGTE_AFWERKHOOGTE" 7 0.18 "CONTINUOUS" "416" "G")
  (list "452" "GW-SLEUF_BODEM" 90 0.18 "CONTINUOUS" "450" "G")
  (list "451" "GW-SLEUF_INSTEEK" 90 0.18 "CONTINUOUS" "450" "G")
  (list "422" "GW-TALUDARCERING_LANG" 90 0.18 "CONTINUOUS" "421" "G")
  (list "423" "GW-TALUDARCERING_KORT" 90 0.18 "CONTINUOUS" "421" "G")
  (list "426" "GW-GRONDWERKLIJN_TEEN" 90 0.18 "CONTINUOUS" "424" "G")
  (list "425" "GW-GRONDWERKLIJN_KRUIN" 90 0.18 "CONTINUOUS" "424" "G")
  (list "514" "GW-WINNINGSVAK_ZAND" 130 0.18 "CONTINUOUS" "511" "G")
  (list "512" "GW-WINNINGSVAK_GRIND" 130 0.18 "CONTINUOUS" "511" "G")
  (list "513" "GW-WINNINGSVAK_KLEI" 130 0.18 "CONTINUOUS" "511" "G")
  (list "455" "GW-CUNET_INSTEEK" 90 0.18 "CONTINUOUS" "454" "G")
  (list "456" "GW-CUNET_BODEM" 90 0.18 "CONTINUOUS" "454" "G")
  (list "466" "GW-WATERGANG_GREPPEL_BODEM" 90 0.18 "CONTINUOUS" "463" "G")
  (list "465" "GW-WATERGANG_GREPPEL_INSTEEK" 90 0.18 "CONTINUOUS" "463" "G")
  (list "464" "GW-WATERGANG_GREPPEL_WATERLIJN" 150 0.18 "CONTINUOUS" "463" "G")
  (list "471" "GW-WATERGANG_SLOOT_BODEM" 90 0.18 "CONTINUOUS" "468" "G")
  (list "470" "GW-WATERGANG_SLOOT_INSTEEK" 90 0.18 "CONTINUOUS" "468" "G")
  (list "469" "GW-WATERGANG_SLOOT_WATERLIJN" 150 0.18 "CONTINUOUS" "468" "G")
  (list "434" "GW-DIJK_KRUIN_BINNEN" 90 0.18 "CONTINUOUS" "433" "G")
  (list "435" "GW-DIJK_KRUIN_BUITEN" 90 0.18 "CONTINUOUS" "433" "G")
  (list "437" "GW-DIJK_TEEN_BINNEN" 90 0.18 "CONTINUOUS" "436" "G")
  (list "438" "GW-DIJK_TEEN_BUITEN" 90 0.18 "CONTINUOUS" "436" "G")
  (list "441" "GW-DIJK_BERM_BUITEN" 90 0.18 "CONTINUOUS" "439" "G")
  (list "440" "GW-DIJK_BERM_BINNEN" 90 0.18 "CONTINUOUS" "439" "G")
  (list "3097" "GW-DIJK_BERM_PLASBERM" 90 0.18 "CONTINUOUS" "439" "G")
  (list "458" "GW-WATERGANG" 90 0.18 "CONTINUOUS" "" "")
  (list "473" "GW-ONTGRAVINGSVAK" 90 0.18 "CONTINUOUS" "" "")
  (list "432" "GW-DIJK" 90 0.18 "CONTINUOUS" "" "")
  (list "446" "GW-WAL" 90 0.18 "CONTINUOUS" "" "")
  (list "442" "GW-OPHOGING" 90 0.18 "CONTINUOUS" "" "")
  (list "416" "GW-HOOGTE" 7 0.18 "CONTINUOUS" "" "")
  (list "431" "GW-BERM" 90 0.18 "CONTINUOUS" "" "")
  (list "520" "GW-PIKETLIJN" 10 0.18 "CONTINUOUS" "" "")
  (list "430" "GW-VOORBELASTING" 90 0.18 "CONTINUOUS" "" "")
  (list "450" "GW-SLEUF" 90 0.18 "CONTINUOUS" "" "")
  (list "421" "GW-TALUDARCERING" 90 0.18 "CONTINUOUS" "" "")
  (list "424" "GW-GRONDWERKLIJN" 90 0.18 "CONTINUOUS" "" "")
  (list "511" "GW-WINNINGSVAK" 130 0.18 "CONTINUOUS" "" "")
  (list "454" "GW-CUNET" 90 0.18 "CONTINUOUS" "" "")
  (list "515" "GW-NIETWINNINGSVAK" 130 0.18 "CONTINUOUS" "" "")
  (list "518" "GW-STORTVAK" 130 0.18 "CONTINUOUS" "" "")
  (list "519" "GW-NIETSTORTVAK" 130 0.18 "CONTINUOUS" "" "")
  (list "415" "GW-RAAI" 10 0.18 "GW-RAAI-SO" "" "")
  (list "501" "GW-GROND_ZAND" 7 0.18 "CONTINUOUS" "477" "G/A")
  (list "480" "GW-GROND_TEELAARDE" 7 0.18 "CONTINUOUS" "477" "G/A")
  (list "485" "GW-GROND_GRIND" 7 0.18 "CONTINUOUS" "477" "G/A")
  (list "489" "GW-GROND_KLEI" 7 0.18 "CONTINUOUS" "477" "G/A")
  (list "493" "GW-GROND_SLIB" 7 0.18 "CONTINUOUS" "477" "G/A")
  (list "509" "GW-GROND_ZAVEL" 7 0.18 "CONTINUOUS" "477" "G/A")
  (list "495" "GW-GROND_STABILISATIE" 7 0.18 "CONTINUOUS" "477" "G/A")
  (list "497" "GW-GROND_STEEN" 7 0.18 "CONTINUOUS" "477" "G/A")
  (list "478" "GW-GROND-WERK" 7 0.18 "CONTINUOUS" "477" "G/A")
  (list "483" "GW-GROND_AFVAL" 7 0.18 "CONTINUOUS" "477" "G/A")
  (list "503" "GW-GROND_ZAND_CUNETZAND" 7 0.18 "CONTINUOUS" "501" "G/A")
  (list "502" "GW-GROND_ZAND-WERK" 7 0.18 "CONTINUOUS" "501" "G/A")
  (list "505" "GW-GROND_ZAND_DRAINEERZAND" 7 0.18 "CONTINUOUS" "501" "G/A")
  (list "507" "GW-GROND_ZAND_FUNDERINGSZAND" 7 0.18 "CONTINUOUS" "501" "G/A")
  (list "492" "GW-GROND_PUIN-WERK" 7 0.18 "CONTINUOUS" "491" "G/A")
  (list "481" "GW-GROND_TEELAARDE-WERK" 7 0.18 "CONTINUOUS" "480" "G/A")
  (list "486" "GW-GROND_GRIND-WERK" 7 0.18 "CONTINUOUS" "485" "G/A")
  (list "488" "GW-GROND_KERNMATERIAAL-WERK" 7 0.18 "CONTINUOUS" "487" "G/A")
  (list "490" "GW-GROND_KLEI-WERK" 7 0.18 "CONTINUOUS" "489" "G/A")
  (list "494" "GW-GROND_SLIB-WERK" 7 0.18 "CONTINUOUS" "493" "G/A")
  (list "510" "GW-GROND_ZAVEL-WERK" 7 0.18 "CONTINUOUS" "509" "G/A")
  (list "500" "GW-GROND_VEEN-WERK" 7 0.18 "CONTINUOUS" "499" "G/A")
  (list "496" "GW-GROND_STABILISATIE-WERK" 7 0.18 "CONTINUOUS" "495" "G/A")
  (list "498" "GW-GROND_STEEN-WERK" 7 0.18 "CONTINUOUS" "497" "G/A")
  (list "484" "GW-GROND_AFVAL-WERK" 7 0.18 "CONTINUOUS" "483" "G/A")
  (list "504" "GW-GROND_ZAND_CUNETZAND-WERK" 7 0.18 "CONTINUOUS" "503" "G/A")
  (list "506" "GW-GROND_ZAND_DRAINEERZAND-WERK" 7 0.18 "CONTINUOUS" "505" "G/A")
  (list "508" "GW-GROND_ZAND_FUNDERINGSZAND-WERK" 7 0.18 "CONTINUOUS" "507" "G/A")
  (list "477" "GW-GROND" 7 0.18 "CONTINUOUS" "" "")
  (list "3005" "GW-GROND_SILTIG" 7 0.18 "CONTINUOUS" "477" "G")
  (list "479" "GW-GROND-OPPERVLAKWERK" 7 0.18 "CONTINUOUS" "477" "G")
  (list "3003" "GW-GROND_HUMEUS" 7 0.18 "CONTINUOUS" "477" "G")
  (list "491" "GW-GROND_PUIN" 7 0.18 "CONTINUOUS" "477" "G")
  (list "3002" "GW-GROND_GRINDIG" 7 0.18 "CONTINUOUS" "477" "G")
  (list "487" "GW-GROND_KERNMATERIAAL" 7 0.18 "CONTINUOUS" "477" "G")
  (list "3001" "GW-GROND_SCHEIDINGLAAG" 7 0.18 "CONTINUOUS" "477" "G")
  (list "3004" "GW-GROND_KLEIIG" 7 0.18 "CONTINUOUS" "477" "G")
  (list "499" "GW-GROND_VEEN" 7 0.18 "CONTINUOUS" "477" "G")
  (list "3006" "GW-GROND_ZANDIG" 7 0.18 "CONTINUOUS" "477" "G")
  (list "482" "GW-GROND_TEELAARDE-OPPERVLAKWERK" 7 0.18 "CONTINUOUS" "480" "G")
  (list "517" "GW-NIETBAGGERVAK" 7 0.25 "CONTINUOUS" "" "")
)) *nlcs-layers*))

; Hulpconstructies (HU) - 1 lagen
(setq *nlcs-layers* (cons (list "HU" "Hulpconstructies" (list
  (list "2810" "HU-HULPCONSTRUCTIES" 7 0.18 "CONTINUOUS" "" "G/A")
)) *nlcs-layers*))

; Inrichtingselementen (IE) - 94 lagen
(setq *nlcs-layers* (cons (list "IE" "Inrichtingselementen" (list
  (list "556" "IE-TERREINAFSCHEIDING_DOORGANG" 210 0.18 "CONTINUOUS" "545" "G/S")
  (list "522" "IE-MEUBILAIR_WEGMEUBILAIR" 7 0.18 "CONTINUOUS" "521" "G/S")
  (list "3574" "IE-MEUBILAIR_TELEFOONCEL" 7 0.18 "CONTINUOUS" "521" "G/S")
  (list "537" "IE-MEUBILAIR_WATERWEGMEUBILAIR" 150 0.18 "CONTINUOUS" "521" "G/S")
  (list "3098" "IE-MEUBILAIR_CAMERA" 7 0.18 "CONTINUOUS" "521" "G/S")
  (list "3385" "IE-MEUBILAIR_DIJKPAAL" 7 0.18 "CONTINUOUS" "521" "G/S")
  (list "3569" "IE-MEUBILAIR_PEUKENPAAL" 7 0.18 "CONTINUOUS" "521" "G/S")
  (list "3573" "IE-MEUBILAIR_SNUFFELPAAL" 7 0.18 "CONTINUOUS" "521" "G/S")
  (list "3387" "IE-MEUBILAIR_FONTEIN" 7 0.18 "CONTINUOUS" "521" "G/S")
  (list "3572" "IE-MEUBILAIR_SCHIJNWERPER" 7 0.18 "CONTINUOUS" "521" "G/S")
  (list "3100" "IE-MEUBILAIR_ZONNEPANEEL" 7 0.18 "CONTINUOUS" "521" "G/S")
  (list "3570" "IE-MEUBILAIR_PICKNICKSET" 7 0.18 "CONTINUOUS" "521" "G/S")
  (list "3386" "IE-MEUBILAIR_OPENBAARTOILET" 7 0.18 "CONTINUOUS" "521" "G/S")
  (list "3575" "IE-MEUBILAIR_WINDZAK" 7 0.18 "CONTINUOUS" "521" "G/S")
  (list "3403" "IE-MEUBILAIR_WEGMEUBILAIR_BRIEVENBUS" 7 0.18 "CONTINUOUS" "522" "G/S")
  (list "3405" "IE-MEUBILAIR_WEGMEUBILAIR_CONTAINER" 7 0.18 "CONTINUOUS" "522" "G/S")
  (list "3563" "IE-MEUBILAIR_WEGMEUBILAIR_BESCHERMBEUGEL" 7 0.18 "CONTINUOUS" "522" "G/S")
  (list "3106" "IE-MEUBILAIR_WEGMEUBILAIR_STROOIRESERVOIR" 7 0.18 "CONTINUOUS" "522" "G/S")
  (list "526" "IE-MEUBILAIR_WEGMEUBILAIR_ABRI" 7 0.18 "CONTINUOUS" "522" "G/S")
  (list "3398" "IE-MEUBILAIR_WEGMEUBILAIR_SPEELTOESTEL" 7 0.18 "CONTINUOUS" "522" "G/S")
  (list "3567" "IE-MEUBILAIR_WEGMEUBILAIR_GRONDSPOT" 7 0.18 "CONTINUOUS" "522" "G/S")
  (list "3564" "IE-MEUBILAIR_WEGMEUBILAIR_DRINKBAK" 7 0.18 "CONTINUOUS" "522" "G/S")
  (list "3566" "IE-MEUBILAIR_WEGMEUBILAIR_GLASBOLREFLECTOR" 7 0.18 "CONTINUOUS" "522" "G/S")
  (list "3406" "IE-MEUBILAIR_WEGMEUBILAIR_FIETSENREK" 7 0.18 "CONTINUOUS" "522" "G/S")
  (list "3395" "IE-MEUBILAIR_WEGMEUBILAIR_PARKEERMAATREGEL" 7 0.18 "CONTINUOUS" "522" "G/S")
  (list "3407" "IE-MEUBILAIR_WEGMEUBILAIR_LICHTMAST" 7 0.18 "CONTINUOUS" "522" "G/S")
  (list "3577" "IE-MEUBILAIR_WEGMEUBILAIR_VERKEERSTEKEN" 7 0.18 "CONTINUOUS" "522" "G/S")
  (list "3410" "IE-MEUBILAIR_WEGMEUBILAIR_VERKEERSBORD" 7 0.18 "CONTINUOUS" "522" "G/S")
  (list "3105" "IE-MEUBILAIR_WEGMEUBILAIR_STADSPLATTEGROND" 7 0.18 "CONTINUOUS" "522" "G/S")
  (list "3412" "IE-MEUBILAIR_WEGMEUBILAIR_VLAGGENMAST" 7 0.18 "CONTINUOUS" "522" "G/S")
  (list "3474" "IE-MEUBILAIR_WEGMEUBILAIR_HALTEPAAL" 7 0.18 "CONTINUOUS" "522" "G/S")
  (list "3399" "IE-MEUBILAIR_WEGMEUBILAIR_TRAP" 7 0.18 "CONTINUOUS" "522" "G/S")
  (list "3390" "IE-MEUBILAIR_WEGMEUBILAIR_SLAGBOOM" 7 0.18 "CONTINUOUS" "522" "G/S")
  (list "3389" "IE-MEUBILAIR_WEGMEUBILAIR_RECLAMEZUIL" 7 0.18 "CONTINUOUS" "522" "G/S")
  (list "3568" "IE-MEUBILAIR_WEGMEUBILAIR_PARKEERAUTOMAAT" 7 0.18 "CONTINUOUS" "522" "G/S")
  (list "3576" "IE-MEUBILAIR_WEGMEUBILAIR_WEGWIJZER" 7 0.18 "CONTINUOUS" "522" "G/S")
  (list "3571" "IE-MEUBILAIR_WEGMEUBILAIR_PRAATPAAL" 7 0.18 "CONTINUOUS" "522" "G/S")
  (list "3397" "IE-MEUBILAIR_WEGMEUBILAIR_TANK" 7 0.18 "CONTINUOUS" "522" "G/S")
  (list "3565" "IE-MEUBILAIR_WEGMEUBILAIR_FLITSPAAL" 7 0.18 "CONTINUOUS" "522" "G/S")
  (list "3402" "IE-MEUBILAIR_WEGMEUBILAIR_BOOMROOSTER" 7 0.18 "CONTINUOUS" "522" "G/S")
  (list "3401" "IE-MEUBILAIR_WEGMEUBILAIR_AFVALBAK" 7 0.18 "CONTINUOUS" "522" "G/S")
  (list "3409" "IE-MEUBILAIR_WEGMEUBILAIR_PAAL" 7 0.18 "CONTINUOUS" "522" "G/S")
  (list "3404" "IE-MEUBILAIR_WEGMEUBILAIR_CAMERA" 7 0.18 "CONTINUOUS" "522" "G/S")
  (list "3388" "IE-MEUBILAIR_WEGMEUBILAIR_ANTENNE" 7 0.18 "CONTINUOUS" "522" "G/S")
  (list "3396" "IE-MEUBILAIR_WEGMEUBILAIR_SCHRIKHEK" 7 0.18 "CONTINUOUS" "522" "G/S")
  (list "3393" "IE-MEUBILAIR_WEGMEUBILAIR_INGANGSCONTROLE" 7 0.18 "CONTINUOUS" "522" "G/S")
  (list "3411" "IE-MEUBILAIR_WEGMEUBILAIR_VERKEERSLICHT" 7 0.18 "CONTINUOUS" "522" "G/S")
  (list "3562" "IE-MEUBILAIR_WATERWEGMEUBILAIR_WATERSTANDMETER" 150 0.18 "CONTINUOUS" "537" "G/S")
  (list "3558" "IE-MEUBILAIR_WATERWEGMEUBILAIR_DUKDALF" 150 0.18 "CONTINUOUS" "537" "G/S")
  (list "541" "IE-MEUBILAIR_WATERWEGMEUBILAIR_BOLDER" 150 0.18 "CONTINUOUS" "537" "G/S")
  (list "3556" "IE-MEUBILAIR_WATERWEGMEUBILAIR_DEBIETMETER" 150 0.18 "CONTINUOUS" "537" "G/S")
  (list "3555" "IE-MEUBILAIR_WATERWEGMEUBILAIR_BOEI" 150 0.18 "CONTINUOUS" "537" "G/S")
  (list "3557" "IE-MEUBILAIR_WATERWEGMEUBILAIR_DRINKBAK" 150 0.18 "CONTINUOUS" "537" "G/S")
  (list "3561" "IE-MEUBILAIR_WATERWEGMEUBILAIR_MERKPAAL" 150 0.18 "CONTINUOUS" "537" "G/S")
  (list "3559" "IE-MEUBILAIR_WATERWEGMEUBILAIR_MEERPAAL" 150 0.18 "CONTINUOUS" "537" "G/S")
  (list "3560" "IE-MEUBILAIR_WATERWEGMEUBILAIR_MEERSTOEL" 150 0.18 "CONTINUOUS" "537" "G/S")
  (list "3414" "IE-AFVAL APART PLAATS" 7 0.18 "CONTINUOUS" "" "G/S")
  (list "3415" "IE-HERDENKINGSMONUMENT" 7 0.18 "CONTINUOUS" "" "G/S")
  (list "3423" "IE-FIETSENKLUIS" 7 0.18 "CONTINUOUS" "" "G/S")
  (list "3417" "IE-SIRENE" 7 0.18 "CONTINUOUS" "" "G/S")
  (list "521" "IE-MEUBILAIR" 7 0.18 "CONTINUOUS" "" "G/S")
  (list "3420" "IE-HOOGTEDETECTIEMETER" 7 0.18 "CONTINUOUS" "" "G/S")
  (list "3418" "IE-WEERSTATION" 7 0.18 "CONTINUOUS" "" "G/S")
  (list "3416" "IE-KUNSTOBJECT" 7 0.18 "CONTINUOUS" "" "G/S")
  (list "3422" "IE-LPG VULPUNT" 7 0.18 "CONTINUOUS" "" "G/S")
  (list "3578" "IE-BORD" 7 0.18 "CONTINUOUS" "" "G/S")
  (list "3421" "IE-INKLIMBEVEILIGING" 7 0.18 "CONTINUOUS" "" "G/S")
  (list "3400" "IE-MEUBILAIR_WEGMEUBILAIR_HOOGSPANNINGSMAST" 7 0.18 "CONTINUOUS" "522" "G/S")
  (list "3104" "IE-MEUBILAIR_WEGMEUBILAIR_SPEELTOESTEL_VALZONE" 7 0.18 "CONTINUOUS" "3398" "G/A")
  (list "552" "IE-TERREINAFSCHEIDING_NATUURLIJK" 60 0.18 "IE-TERREINAFSCHEIDING_NATUURLIJK-SO" "545" "G")
  (list "546" "IE-TERREINAFSCHEIDING_KUNSTMATIG" 30 0.18 "IE-TERREINAFSCHEIDING_KUNSTMATIG-SO" "545" "G")
  (list "544" "IE-MEUBILAIR_LUCHTHAVENMEUBILAIR" 130 0.18 "CONTINUOUS" "521" "G")
  (list "543" "IE-MEUBILAIR_SPOORWEGMEUBILAIR" 30 0.18 "CONTINUOUS" "521" "G")
  (list "553" "IE-TERREINAFSCHEIDING_NATUURLIJK_HAAG" 60 0.18 "IE-TERREINAFSCHEIDING_NATUURLIJK-SO" "552" "G")
  (list "555" "IE-TERREINAFSCHEIDING_NATUURLIJK_HOUTWAL" 60 0.18 "IE-TERREINAFSCHEIDING_NATUURLIJK-SO" "552" "G")
  (list "554" "IE-TERREINAFSCHEIDING_NATUURLIJK_HAAG MET RASTER" 60 0.18 "IE-TERREINAFSCHEIDING_NATUURLIJK-SO" "552" "G")
  (list "548" "IE-TERREINAFSCHEIDING_KUNSTMATIG_HEKWERK" 20 0.18 "IE-TERREINAFSCHEIDING_KUNSTMATIG-SO" "546" "G")
  (list "551" "IE-TERREINAFSCHEIDING_KUNSTMATIG_SCHUTTING" 90 0.18 "IE-TERREINAFSCHEIDING_KUNSTMATIG-SO" "546" "G")
  (list "547" "IE-TERREINAFSCHEIDING_KUNSTMATIG_RASTERHEKWERK" 20 0.18 "IE-TERREINAFSCHEIDING_KUNSTMATIG-SO" "546" "G")
  (list "550" "IE-TERREINAFSCHEIDING_KUNSTMATIG_MUUR" 90 0.18 "IE-TERREINAFSCHEIDING_KUNSTMATIG-SO" "546" "G")
  (list "3101" "IE-MEUBILAIR_WEGMEUBILAIR_FONTEIN" 7 0.18 "CONTINUOUS" "522" "G")
  (list "3413" "IE-MEUBILAIR_WEGMEUBILAIR_ZITBANK" 7 0.18 "CONTINUOUS" "522" "G/S")
  (list "540" "IE-MEUBILAIR_WATERWEGMEUBILAIR_LOOPBRUG" 150 0.18 "CONTINUOUS" "537" "G")
  (list "542" "IE-MEUBILAIR_WATERWEGMEUBILAIR_AFMEERCONSTRUCTIE" 150 0.18 "CONTINUOUS" "537" "G")
  (list "538" "IE-MEUBILAIR_WATERWEGMEUBILAIR_DRIJFRAAM" 150 0.18 "CONTINUOUS" "537" "G")
  (list "539" "IE-MEUBILAIR_WATERWEGMEUBILAIR_VLONDER" 150 0.18 "CONTINUOUS" "537" "G")
  (list "2909" "IE-MEUBILAIR_WATERWEGMEUBILAIR_PLANKIER" 150 0.18 "CONTINUOUS" "537" "G")
  (list "3110" "IE-TERREINAFSCHEIDING_KUNSTMATIG_HEKWERK_LAAG" 210 0.18 "CONTINUOUS" "548" "G")
  (list "549" "IE-TERREINAFSCHEIDING_KUNSTMATIG_HEKWERK_RASTER" 30 0.18 "IE-TERREINAFSCHEIDING_KUNSTMATIG-SO" "548" "G")
  (list "3108" "IE-TERREINAFSCHEIDING_KUNSTMATIG_HEKWERK_HOOG" 210 0.18 "CONTINUOUS" "548" "G")
  (list "3109" "IE-TERREINAFSCHEIDING_KUNSTMATIG_HEKWERK_HOOG_BALLENVANGER" 210 0.18 "CONTINUOUS" "3108" "G")
  (list "545" "IE-TERREINAFSCHEIDING" 210 0.18 "IE-TERREINAFSCHEIDING-SO" "" "G")
  (list "3419" "IE-BALUSTRADE" 7 0.18 "CONTINUOUS" "" "G")
  (list "3099" "IE-MEUBILAIR_SPEELPLEK" 7 0.18 "CONTINUOUS" "521" "G")
)) *nlcs-layers*))

; Installaties Vaarweg (IV) - 3 lagen
(setq *nlcs-layers* (cons (list "IV" "Installaties Vaarweg" (list
  (list "2539" "IV-DRI_DRAAGCONSTRUCTIE" 7 0.18 "CONTINUOUS" "2538" "G")
  (list "2544" "IV-LICHTOPSTAND" 170 0.18 "CONTINUOUS" "" "G")
  (list "2538" "IV-DRI" 170 0.18 "CONTINUOUS" "" "G")
)) *nlcs-layers*))

; Installaties Wegen (IW) - 15 lagen
(setq *nlcs-layers* (cons (list "IW" "Installaties Wegen" (list
  (list "3353" "IW-TRAMSIGNALERING_PAAL" 7 0.18 "CONTINUOUS" "3352" "G/S")
  (list "3354" "IW-TRAMSIGNALERING_PORTAAL" 7 0.18 "CONTINUOUS" "3352" "G/S")
  (list "3355" "IW-VRI_POLLER" 7 0.18 "CONTINUOUS" "2644" "G/S")
  (list "3352" "IW-TRAMSIGNALERING" 7 0.18 "CONTINUOUS" "" "G/S")
  (list "2644" "IW-VRI" 160 0.18 "CONTINUOUS" "" "G/S")
  (list "2642" "IW-TDI" 160 0.18 "CONTINUOUS" "" "G/S")
  (list "2646" "IW-VS" 160 0.18 "CONTINUOUS" "" "G/S")
  (list "2645" "IW-VRI_DRAAGCONSTRUCTIE" 160 0.18 "CONTINUOUS" "2644" "G")
  (list "2643" "IW-TDI_DRAAGCONSTRUCTIE" 160 0.18 "CONTINUOUS" "2642" "G")
  (list "2649" "IW-DRIP_DRAAGCONSTRUCTIE" 160 0.18 "CONTINUOUS" "2648" "G")
  (list "2647" "IW-VS_DRAAGCONSTRUCTIE" 160 0.18 "CONTINUOUS" "2646" "G")
  (list "3506" "IW-VRI_DRAAGCONSTRUCTIE_PORTAAL" 160 0.18 "CONTINUOUS" "2645" "G")
  (list "3505" "IW-VRI_DRAAGCONSTRUCTIE_PAAL" 160 0.18 "CONTINUOUS" "2645" "G")
  (list "2648" "IW-DRIP" 160 0.18 "CONTINUOUS" "" "G")
  (list "2653" "IW-TELECOM" 80 0.18 "CONTINUOUS" "" "G")
)) *nlcs-layers*))

; Kunststofconstructies (KC) - 14 lagen
(setq *nlcs-layers* (cons (list "KC" "Kunststofconstructies" (list
  (list "2815" "KC-VERBINDING_BOUT" 140 0.18 "CONTINUOUS" "2814" "G/A")
  (list "2816" "KC-VERBINDING_STAAL" 140 0.18 "CONTINUOUS" "2814" "G/A")
  (list "2819" "KC-AANGRENZENDE CONSTRUCTIE_HOUT" 7 0.18 "CONTINUOUS" "2817" "G/A")
  (list "2818" "KC-AANGRENZENDE CONSTRUCTIE_BETON" 7 0.18 "CONTINUOUS" "2817" "G/A")
  (list "2821" "KC-AANGRENZENDE CONSTRUCTIE_METSELWERK" 7 0.18 "CONTINUOUS" "2817" "G/A")
  (list "2820" "KC-AANGRENZENDE CONSTRUCTIE_STAAL" 7 0.18 "CONTINUOUS" "2817" "G/A")
  (list "2811" "KC-KUNSTSTOFVORM" 40 0.18 "CONTINUOUS" "" "G/A")
  (list "2813" "KC-KUNSTSTOFVORM_PLAAT" 40 0.18 "CONTINUOUS" "2811" "G")
  (list "2812" "KC-KUNSTSTOFVORM_BALK" 40 0.18 "CONTINUOUS" "2811" "G")
  (list "2823" "KC-REPARATIES" 170 0.18 "CONTINUOUS" "" "G")
  (list "2814" "KC-VERBINDING" 140 0.18 "CONTINUOUS" "" "G")
  (list "2817" "KC-AANGRENZENDE CONSTRUCTIE" 7 0.18 "CONTINUOUS" "" "G")
  (list "2822" "KC-OVERIG MATERIAAL" 7 0.18 "CONTINUOUS" "" "G")
  (list "2824" "KC-LEVENSDUURVERLENGENDE MAATREGEL" 170 0.18 "CONTINUOUS" "" "G")
)) *nlcs-layers*))

; Kadastrale grenzen (KG) - 67 lagen
(setq *nlcs-layers* (cons (list "KG" "Kadastrale grenzen" (list
  (list "611" "KG-KADASTRAAL" 170 0.18 "CONTINUOUS" "" "G/S")
  (list "598" "KG-GRONDEIGENDOM" 130 0.18 "CONTINUOUS" "" "G/A")
  (list "3115" "KG-GRENS_RAMING" 7 0.18 "KG-RAMING-SO" "557" "G")
  (list "569" "KG-GRENS_OPNAME" 210 0.18 "KG-OPNAME-SO" "557" "G")
  (list "3116" "KG-GRENS_UITGEEFBAAR GEBIED" 7 0.18 "KG-UITGEEFBAARGEBIED-SO" "557" "G")
  (list "3113" "KG-GRENS_WIJZIGING" 7 0.18 "CONTINUOUS" "557" "G")
  (list "3111" "KG-GRENS_VLAKAFSLUITER" 7 0.18 "CONTINUOUS" "557" "G")
  (list "3112" "KG-GRENS_WIJK" 210 0.18 "CONTINUOUS" "557" "G")
  (list "564" "KG-GRENS_PACHT" 150 0.18 "KG-PACHT-SO" "557" "G")
  (list "3507" "KG-GRENS_AANKOOP" 130 0.18 "KG-GVAANKOOP-SO" "557" "G")
  (list "570" "KG-GRENS_OVERHOEK" 150 0.18 "CONTINUOUS" "557" "G")
  (list "3117" "KG-GRENS_VERKOOP" 7 0.18 "KG-VERKOOP-SO" "557" "G")
  (list "3508" "KG-GRENS_ONTEIGENING" 130 0.18 "CONTINUOUS" "557" "G")
  (list "599" "KG-GRONDEIGENDOM_RIJK" 130 0.18 "CONTINUOUS" "598" "G")
  (list "606" "KG-GRONDEIGENDOM_PROVINCIE" 130 0.18 "CONTINUOUS" "598" "G")
  (list "607" "KG-GRONDEIGENDOM_GEMEENTE" 130 0.18 "CONTINUOUS" "598" "G")
  (list "610" "KG-GRONDEIGENDOM_PARTICULIER" 130 0.18 "CONTINUOUS" "598" "G")
  (list "609" "KG-GRONDEIGENDOM_WATERSCHAP" 130 0.18 "CONTINUOUS" "598" "G")
  (list "608" "KG-GRONDEIGENDOM_PRORAIL" 130 0.18 "CONTINUOUS" "598" "G")
  (list "576" "KG-BEHEERGRENS_WATERSCHAP" 170 0.18 "KG-BGWATERSCHAP-SO" "572" "G")
  (list "573" "KG-BEHEERGRENS_PROVINCIE" 170 0.18 "KG-BGPROVINCIE-SO" "572" "G")
  (list "574" "KG-BEHEERGRENS_GEMEENTE" 170 0.18 "KG-BGGEMEENTE-SO" "572" "G")
  (list "577" "KG-BEHEERGRENS_RIJK" 170 0.18 "KG-BGRIJK-SO" "572" "G")
  (list "575" "KG-BEHEERGRENS_PRORAIL" 170 0.18 "KG-BGPRORAIL-SO" "572" "G")
  (list "589" "KG-BENOGRENS_PRORAIL" 170 0.18 "KG-BENOGPRORAIL-SO" "586" "G")
  (list "591" "KG-BENOGRENS_RIJK" 170 0.18 "KG-BENOGRIJK-SO" "586" "G")
  (list "590" "KG-BENOGRENS_WATERSCHAP" 170 0.18 "KG-BENOGWATERSCHAP-SO" "586" "G")
  (list "588" "KG-BENOGRENS_GEMEENTE" 170 0.18 "KG-BENOGGEMEENTE-SO" "586" "G")
  (list "587" "KG-BENOGRENS_PROVINCIE" 170 0.18 "KG-BENOGPROVINCIE-SO" "586" "G")
  (list "615" "KG-KADASTRAAL_NOK" 10 0.18 "CONTINUOUS" "611" "G")
  (list "614" "KG-KADASTRAAL_DAKRAND" 170 0.18 "CONTINUOUS" "611" "G")
  (list "612" "KG-KADASTRAAL_ROOILIJN" 170 0.18 "CONTINUOUS" "611" "G")
  (list "613" "KG-KADASTRAAL_BEBOUWING" 170 0.18 "CONTINUOUS" "611" "G")
  (list "597" "KG-GRONDVERWERVING_ONTEIGENING" 130 0.18 "CONTINUOUS" "593" "G")
  (list "594" "KG-GRONDVERWERVING_AANKOOP" 130 0.18 "KG-GVAANKOOP-SO" "593" "G")
  (list "595" "KG-GRONDVERWERVING_VERKOOP" 130 0.18 "CONTINUOUS" "593" "G")
  (list "596" "KG-GRONDVERWERVING_OPSTALLEN" 130 0.18 "CONTINUOUS" "593" "G")
  (list "582" "KG-ONDERHOUDGRENS_PRORAIL" 170 0.18 "KG-OGPRORAIL-SO" "579" "G")
  (list "584" "KG-ONDERHOUDGRENS_RIJK" 170 0.18 "KG-OGRIJK-SO" "579" "G")
  (list "580" "KG-ONDERHOUDGRENS_PROVINCIE" 170 0.18 "KG-OGPROVINCIE-SO" "579" "G")
  (list "583" "KG-ONDERHOUDGRENS_WATERSCHAP" 170 0.18 "KG-OGWATERSCHAP-SO" "579" "G")
  (list "581" "KG-ONDERHOUDGRENS_GEMEENTE" 170 0.18 "KG-OGGEMEENTE-SO" "579" "G")
  (list "600" "KG-GRONDEIGENDOM_RIJK_VROM" 130 0.18 "CONTINUOUS" "599" "G")
  (list "601" "KG-GRONDEIGENDOM_RIJK_DEFENSIE" 130 0.18 "CONTINUOUS" "599" "G")
  (list "604" "KG-GRONDEIGENDOM_RIJK_FINANCIEN" 130 0.18 "CONTINUOUS" "599" "G")
  (list "605" "KG-GRONDEIGENDOM_RIJK_VENW" 130 0.18 "CONTINUOUS" "599" "G")
  (list "602" "KG-GRONDEIGENDOM_RIJK_DOMEINEN" 130 0.18 "CONTINUOUS" "599" "G")
  (list "603" "KG-GRONDEIGENDOM_RIJK_LANDBOUW" 130 0.18 "CONTINUOUS" "599" "G")
  (list "592" "KG-BENOGRENS_RIJK_RWS" 170 0.18 "KG-BENOGRIJKRWS-SO" "591" "G")
  (list "585" "KG-ONDERHOUDGRENS_RIJK_RWS" 170 0.18 "KG-OGRIJKRWS-SO" "584" "G")
  (list "557" "KG-GRENS" 150 0.18 "CONTINUOUS" "" "G")
  (list "572" "KG-BEHEERGRENS" 170 0.18 "KG-BG-SO" "" "G")
  (list "586" "KG-BENOGRENS" 170 0.18 "KG-BENOG-SO" "" "G")
  (list "593" "KG-GRONDVERWERVING" 130 0.18 "KG-GV-SO" "" "G")
  (list "579" "KG-ONDERHOUDGRENS" 170 0.18 "KG-OG-SO" "" "G")
  (list "4035" "KG-KADASTRAAL_PAND" 170 0.18 "CONTINUOUS" "611" "G")
  (list "565" "KG-GRENS_KADASTRAAL" 150 0.18 "KG-KADASTRAAL-SO" "557" "G")
  (list "566" "KG-GRENS_PERCEEL" 150 0.18 "KG-PERCEEL-SO" "557" "G")
  (list "567" "KG-GRENS_SECTIE" 150 0.18 "KG-SECTIE-SO" "557" "G")
  (list "563" "KG-GRENS_GRONDWATERBESCHERMINGSGEBIED" 150 0.18 "KG-GWBG-SO" "557" "G")
  (list "568" "KG-GRENS_RIJKSEIGENDOM" 150 0.18 "KG-RIJKSEIGENDOM-SO" "557" "G")
  (list "578" "KG-BEHEERGRENS_RIJK_RWS" 170 0.18 "KG-BGRIJKRWS-SO" "577" "G")
  (list "560" "KG-GRENS_GEMEENTE" 150 0.18 "KG-GEMEENTE-SO" "557" "G")
  (list "562" "KG-GRENS_BESTEMMINGSPLAN" 150 0.18 "KG-BESTEMMINGSPLAN-SO" "557" "G")
  (list "561" "KG-GRENS_WATERSCHAP" 150 0.18 "KG-WATERSCHAP-SO" "557" "G")
  (list "558" "KG-GRENS_LAND" 150 0.18 "KG-LAND-SO" "557" "G")
  (list "559" "KG-GRENS_PROVINCIE" 150 0.18 "KG-PROVINCIE-SO" "557" "G")
)) *nlcs-layers*))

; Kabels en leidingen (KL) - 761 lagen
(setq *nlcs-layers* (cons (list "KL" "Kabels en leidingen" (list
  (list "621" "KL-BRANDSTOF_HULPSTUK" 40 0.18 "CONTINUOUS" "620" "G/S")
  (list "627" "KL-BRANDSTOF_LOCATIEPAAL" 40 0.18 "CONTINUOUS" "620" "G/S")
  (list "631" "KL-BRANDSTOF_TANK" 40 0.18 "CONTINUOUS" "620" "G/S")
  (list "630" "KL-BRANDSTOF_PUT" 40 0.18 "CONTINUOUS" "620" "G/S")
  (list "1244" "KL-WARMTENET_BRONPUT" 80 0.18 "CONTINUOUS" "1232" "G/S")
  (list "1245" "KL-WARMTENET_HULPSTUK" 80 0.18 "CONTINUOUS" "1232" "G/S")
  (list "1249" "KL-WARMTENET_LOCATIEPAAL" 80 0.18 "KL-WARMTENET-SO" "1232" "G/S")
  (list "1252" "KL-WARMTENET_PUT" 80 0.18 "CONTINUOUS" "1232" "G/S")
  (list "3122" "KL-POLLER_KAST" 7 0.18 "CONTINUOUS" "3121" "G/S")
  (list "641" "KL-CHEMIE_LOCATIEPAAL" 40 0.18 "CONTINUOUS" "637" "G/S")
  (list "644" "KL-CHEMIE_PUT" 40 0.18 "CONTINUOUS" "637" "G/S")
  (list "639" "KL-CHEMIE_HULPSTUK" 40 0.18 "CONTINUOUS" "637" "G/S")
  (list "1348" "KL-WATER_HULPSTUK" 170 0.18 "CONTINUOUS" "1264" "G/S")
  (list "1361" "KL-WATER_PUT" 170 0.18 "CONTINUOUS" "1264" "G/S")
  (list "1356" "KL-WATER_INKOOPPUNT" 170 0.18 "CONTINUOUS" "1264" "G/S")
  (list "1364" "KL-WATER_STRAATPOT" 170 0.18 "CONTINUOUS" "1264" "G/S")
  (list "1357" "KL-WATER_LOCATIEPAAL" 170 0.18 "CONTINUOUS" "1264" "G/S")
  (list "3429" "KL-TELPUNT_TELKAST" 100 0.18 "CONTINUOUS" "1400" "G/S")
  (list "1174" "KL-GAS_LOKATIEPAAL" 30 0.18 "CONTINUOUS" "998" "G/S")
  (list "1176" "KL-GAS_PUT" 30 0.18 "CONTINUOUS" "998" "G/S")
  (list "1102" "KL-GAS_HULPSTUK" 30 0.18 "CONTINUOUS" "998" "G/S")
  (list "1111" "KL-GAS_INKOOPPUNT" 30 0.18 "CONTINUOUS" "998" "G/S")
  (list "3428" "KL-GAS_TERREINKAST" 30 0.18 "CONTINUOUS" "998" "G/S")
  (list "839" "KL-DATA_ZENDMAST" 90 0.18 "CONTINUOUS" "720" "G/S")
  (list "782" "KL-DATA_KAST" 90 0.18 "CONTINUOUS" "720" "G/S")
  (list "750" "KL-DATA_GLASVEZEL" 90 0.18 "KL-GLASVEZEL-SO" "720" "G/S")
  (list "781" "KL-DATA_KABELROL" 90 0.18 "CONTINUOUS" "720" "G/S")
  (list "3426" "KL-DATA_TELPAAL" 90 0.18 "CONTINUOUS" "720" "G/S")
  (list "2910" "KL-DATA_SIGNAALGEVER" 90 0.18 "CONTINUOUS" "720" "G/S")
  (list "3424" "KL-DATA_RADARMAST" 90 0.18 "CONTINUOUS" "720" "G/S")
  (list "761" "KL-DATA_HULPSTUK" 90 0.18 "CONTINUOUS" "720" "G/S")
  (list "3425" "KL-DATA_STRAALZENDER" 90 0.18 "CONTINUOUS" "720" "G/S")
  (list "878" "KL-ET_LS" 190 0.18 "KL-LS-SO" "840" "G/S")
  (list "863" "KL-ET_HS" 10 0.18 "KL-HS-SO" "840" "G/S")
  (list "841" "KL-ET_AARDING" 7 0.18 "KL-AARDING-SO" "840" "G/S")
  (list "874" "KL-ET_HULPSTUK" 10 0.18 "CONTINUOUS" "840" "G/S")
  (list "968" "KL-ET_LICHTGEVOELIGE CEL" 10 0.18 "CONTINUOUS" "840" "S")
  (list "1224" "KL-OLIE_HULPSTUK" 40 0.18 "CONTINUOUS" "1222" "G/S")
  (list "1229" "KL-OLIE_PUT" 40 0.18 "CONTINUOUS" "1222" "G/S")
  (list "1226" "KL-OLIE_LOCATIEPAAL" 40 0.18 "CONTINUOUS" "1222" "G/S")
  (list "677" "KL-CV_LOCATIEPAAL" 40 0.18 "CONTINUOUS" "645" "G/S")
  (list "673" "KL-CV_HULPSTUK" 40 0.18 "CONTINUOUS" "645" "G/S")
  (list "1203" "KL-KOUDENET_PUT" 130 0.18 "CONTINUOUS" "1183" "G/S")
  (list "1195" "KL-KOUDENET_BRONPUT" 130 0.18 "CONTINUOUS" "1183" "G/S")
  (list "1196" "KL-KOUDENET_HULPSTUK" 130 0.18 "CONTINUOUS" "1183" "G/S")
  (list "1200" "KL-KOUDENET_LOCATIEPAAL" 130 0.18 "CONTINUOUS" "1183" "G/S")
  (list "1267" "KL-WATER_BEREGENING_HULPSTUK" 153 0.18 "CONTINUOUS" "1265" "G/S")
  (list "1275" "KL-WATER_BEREGENING_LOCATIEPAAL" 150 0.18 "KL-WATER-SO" "1265" "G/S")
  (list "1278" "KL-WATER_BEREGENING_SPROEIER" 150 0.18 "KL-WATER-SO" "1265" "G/S")
  (list "1301" "KL-WATER_BRANDLEIDING_HULPSTUK" 150 0.18 "CONTINUOUS" "1280" "G/S")
  (list "1281" "KL-WATER_BRANDLEIDING_BRANDHYDRANT" 150 0.18 "CONTINUOUS" "1280" "G/S")
  (list "1310" "KL-WATER_BRANDLEIDING_PUT" 150 0.18 "CONTINUOUS" "1280" "G/S")
  (list "1309" "KL-WATER_BRANDLEIDING_LOCATIEPAAL" 150 0.18 "CONTINUOUS" "1280" "G/S")
  (list "1362" "KL-WATER_PUT_POMPPUT" 170 0.18 "CONTINUOUS" "1361" "G/S")
  (list "1110" "KL-GAS_HULPSTUK_STRAATPOT" 30 0.18 "CONTINUOUS" "1102" "G/S")
  (list "791" "KL-DATA_SIGNAALKABEL_HULPSTUK" 90 0.18 "CONTINUOUS" "789" "G/S")
  (list "795" "KL-DATA_SIGNAALKABEL_KAST" 90 0.18 "KL-SIGNAALKABEL-SO" "789" "G/S")
  (list "833" "KL-DATA_WAN_KAST" 90 0.18 "CONTINUOUS" "827" "G/S")
  (list "829" "KL-DATA_WAN_HULPSTUK" 90 0.18 "CONTINUOUS" "827" "G/S")
  (list "739" "KL-DATA_DEFENSIE_HULPSTUK" 90 0.18 "CONTINUOUS" "737" "G/S")
  (list "743" "KL-DATA_DEFENSIE_KAST" 90 0.18 "CONTINUOUS" "737" "G/S")
  (list "807" "KL-DATA_STUURKABEL_KAST" 90 0.18 "KL-STUURKABEL-SO" "801" "G/S")
  (list "803" "KL-DATA_STUURKABEL_HULPSTUK" 90 0.18 "CONTINUOUS" "801" "G/S")
  (list "816" "KL-DATA_TELECOM_HULPSTUK" 90 0.18 "CONTINUOUS" "814" "G/S")
  (list "820" "KL-DATA_TELECOM_KAST" 90 0.18 "CONTINUOUS" "814" "G/S")
  (list "755" "KL-DATA_GLASVEZEL_KAST" 90 0.18 "CONTINUOUS" "750" "G/S")
  (list "751" "KL-DATA_GLASVEZEL_HULPSTUK" 90 0.18 "CONTINUOUS" "750" "G/S")
  (list "767" "KL-DATA_INTERCOM_HULPSTUK" 90 0.18 "CONTINUOUS" "765" "G/S")
  (list "771" "KL-DATA_INTERCOM_KAST" 90 0.18 "CONTINUOUS" "765" "G/S")
  (list "729" "KL-DATA_CAI_KAST" 90 0.18 "CONTINUOUS" "724" "G/S")
  (list "725" "KL-DATA_CAI_HULPSTUK" 90 0.18 "CONTINUOUS" "724" "G/S")
  (list "977" "KL-ET_MS_HULPSTUK" 130 0.18 "CONTINUOUS" "973" "G/S")
  (list "984" "KL-ET_MS_TRANSFORMATORSTATION" 130 0.18 "CONTINUOUS" "973" "G/S")
  (list "981" "KL-ET_MS_KABELROL" 130 0.18 "CONTINUOUS" "973" "G/S")
  (list "884" "KL-ET_LS_KABELROL" 190 0.18 "CONTINUOUS" "878" "G/S")
  (list "879" "KL-ET_LS_HULPSTUK" 190 0.18 "CONTINUOUS" "878" "G/S")
  (list "873" "KL-ET_HS_TRANSFORMATORSTATION" 10 0.18 "CONTINUOUS" "863" "G/S")
  (list "866" "KL-ET_HS_HULPSTUK" 10 0.18 "CONTINUOUS" "863" "G/S")
  (list "870" "KL-ET_HS_KABELROL" 10 0.18 "CONTINUOUS" "863" "G/S")
  (list "993" "KL-ET_ZHS_KABELROL" 10 0.18 "CONTINUOUS" "986" "G/S")
  (list "989" "KL-ET_ZHS_HULPSTUK" 10 0.18 "CONTINUOUS" "986" "G/S")
  (list "996" "KL-ET_ZHS_TRANSFORMATORSTATION" 10 0.18 "CONTINUOUS" "986" "G/S")
  (list "857" "KL-ET_AARDING_KAST" 7 0.18 "CONTINUOUS" "841" "G/S")
  (list "953" "KL-ET_LS_SR_KAST" 190 0.18 "CONTINUOUS" "918" "G/S")
  (list "964" "KL-ET_LS_VOEDINGSKABEL_KABELROL" 190 0.18 "CONTINUOUS" "961" "G/S")
  (list "3121" "KL-POLLER" 7 0.18 "CONTINUOUS" "" "")
  (list "3123" "KL-WARMTEOPSLAGSYSTEEM" 7 0.18 "CONTINUOUS" "" "")
  (list "1404" "KL-MONITORING" 120 0.18 "CONTINUOUS" "" "")
  (list "1408" "KL-VRI" 30 0.18 "CONTINUOUS" "" "")
  (list "1392" "KL-GMS" 20 0.18 "CONTINUOUS" "" "")
  (list "1420" "KL-POMP" 230 0.18 "CONTINUOUS" "" "")
  (list "3481" "KL-KOUDEOPSLAGSYSTEEM" 140 0.18 "CONTINUOUS" "" "")
  (list "636" "KL-BRANDSTOF_VULPUNT" 40 0.18 "CONTINUOUS" "620" "G")
  (list "628" "KL-BRANDSTOF_MANTELBUIS" 40 0.18 "CONTINUOUS" "620" "G")
  (list "632" "KL-BRANDSTOF_TRANSPORTLEIDING" 40 0.18 "KL-BRANDSTOF-SO" "620" "G")
  (list "1253" "KL-WARMTENET_TRANSPORTLEIDING" 80 0.18 "KL-WARMTENET-SO" "1232" "G")
  (list "1233" "KL-WARMTENET_AANSLUITLEIDING" 80 0.18 "KL-WARMTENET-SO" "1232" "G")
  (list "1250" "KL-WARMTENET_MANTELBUIS" 80 0.18 "CONTINUOUS" "1232" "G")
  (list "642" "KL-CHEMIE_MANTELBUIS" 40 0.18 "CONTINUOUS" "637" "G")
  (list "638" "KL-CHEMIE_AFSLUITER" 40 0.18 "CONTINUOUS" "637" "G")
  (list "640" "KL-CHEMIE_LEIDING" 40 0.18 "KL-CHEMIE-SO" "637" "G")
  (list "1419" "KL-CCTV_KABEL" 70 0.18 "CONTINUOUS" "1418" "G")
  (list "1331" "KL-WATER_HUISAANSLUITING" 170 0.18 "KL-WATER-SO" "1264" "G")
  (list "1265" "KL-WATER_BEREGENING" 150 0.18 "KL-WATER-SO" "1264" "G")
  (list "1280" "KL-WATER_BRANDLEIDING" 150 0.18 "KL-WATER-SO" "1264" "G")
  (list "1365" "KL-WATER_TRANSPORTLEIDING" 170 0.18 "KL-WATER-SO" "1264" "G")
  (list "1358" "KL-WATER_MANTELBUIS" 170 0.18 "CONTINUOUS" "1264" "G")
  (list "1359" "KL-WATER_OOGDOUCHE" 170 0.18 "CONTINUOUS" "1264" "G")
  (list "1384" "KL-WATER_WATERBRON" 170 0.18 "CONTINUOUS" "1264" "G")
  (list "1415" "KL-VEVA_KABEL" 60 0.18 "CONTINUOUS" "1414" "G")
  (list "1401" "KL-TELPUNT_KABEL" 100 0.18 "KL-TELPUNT-SO" "1400" "G")
  (list "999" "KL-GAS_HD" 30 0.18 "KL-GAS_HD-SO" "998" "G")
  (list "1112" "KL-GAS_LD" 50 0.18 "KL-GAS_LD-SO" "998" "G")
  (list "1175" "KL-GAS_MANTELBUIS" 30 0.18 "CONTINUOUS" "998" "G")
  (list "1178" "KL-GAS_STATION" 30 0.18 "CONTINUOUS" "998" "G")
  (list "1389" "KL-DRIP_KABEL" 170 0.18 "KL-DRIP-SO" "1388" "G")
  (list "789" "KL-DATA_SIGNAALKABEL" 90 0.18 "KL-SIGNAALKABEL-SO" "720" "G")
  (list "827" "KL-DATA_WAN" 90 0.18 "KL-WAN-SO" "720" "G")
  (list "737" "KL-DATA_DEFENSIE" 90 0.18 "KL-DEF-SO" "720" "G")
  (list "801" "KL-DATA_STUURKABEL" 90 0.18 "KL-STUURKABEL-SO" "720" "G")
  (list "722" "KL-DATA_ALGEMEEN" 90 0.18 "CONTINUOUS" "720" "G")
  (list "788" "KL-DATA_RESERVE" 90 0.18 "CONTINUOUS" "720" "G")
  (list "814" "KL-DATA_TELECOM" 90 0.18 "KL-TELECOM-SO" "720" "G")
  (list "778" "KL-DATA_KABELBUNDEL" 90 0.18 "CONTINUOUS" "720" "G")
  (list "786" "KL-DATA_MANTELBUIS" 90 0.18 "CONTINUOUS" "720" "G")
  (list "780" "KL-DATA_KABELKOKER" 90 0.18 "CONTINUOUS" "720" "G")
  (list "765" "KL-DATA_INTERCOM" 90 0.18 "KL-TELECOM-SO" "720" "G")
  (list "721" "KL-DATA_LOZE LEIDING" 90 0.18 "CONTINUOUS" "720" "G")
  (list "724" "KL-DATA_CAI" 90 0.18 "KL-CAI-SO" "720" "G")
  (list "779" "KL-DATA_KABELGOOT" 90 0.18 "CONTINUOUS" "720" "G")
  (list "1417" "KL-AFSLUITINSTALLATIE_KABEL" 60 0.18 "CONTINUOUS" "1416" "G")
  (list "1411" "KL-UWKS_KABEL" 130 0.18 "KL-UWKS-SO" "1410" "G")
  (list "2958" "KL-SCHEMA_RASTERINDELING" 7 0.18 "CONTINUOUS" "2950" "G")
  (list "2963" "KL-SCHEMA_VOEDINGSLIJN" 30 0.18 "CONTINUOUS" "2950" "G")
  (list "2962" "KL-SCHEMA_MECHANISCHEKOPPELING" 7 0.18 "CONTINUOUS" "2950" "G")
  (list "2955" "KL-SCHEMA_GOOT" 7 0.18 "CONTINUOUS" "2950" "G")
  (list "2956" "KL-SCHEMA_KABEL" 50 0.18 "CONTINUOUS" "2950" "G")
  (list "2957" "KL-SCHEMA_KLEMMENSTROOK" 7 0.18 "CONTINUOUS" "2950" "G")
  (list "2952" "KL-SCHEMA_BEHUIZING" 10 0.18 "ZZ-DASHDOT-SO" "2950" "G")
  (list "2951" "KL-SCHEMA_AARDRAIL" 90 0.18 "ZZ-CENTER-SO" "2950" "G")
  (list "2953" "KL-SCHEMA_COMPONENT" 10 0.18 "CONTINUOUS" "2950" "G")
  (list "2954" "KL-SCHEMA_DIAGRAM" 7 0.18 "CONTINUOUS" "2950" "G")
  (list "1387" "KL-BEWEGWIJZERING_KABEL" 210 0.18 "KL-BEWEGWIJZERING-SO" "1386" "G")
  (list "973" "KL-ET_MS" 130 0.18 "KL-MS-SO" "840" "G")
  (list "986" "KL-ET_ZHS" 10 0.18 "KL-ZHS-SO" "840" "G")
  (list "3427" "KL-ET_DVM" 10 0.18 "CONTINUOUS" "840" "G/S")
  (list "862" "KL-ET_LOZE LEIDING" 10 0.18 "CONTINUOUS" "840" "G")
  (list "969" "KL-ET_MANTELBUIS" 10 0.18 "CONTINUOUS" "840" "G")
  (list "1231" "KL-TRACE_WENSTRACE" 7 0.18 "ZZ-HIDDEN-SO" "1230" "G")
  (list "1227" "KL-OLIE_MANTELBUIS" 40 0.18 "CONTINUOUS" "1222" "G")
  (list "1228" "KL-OLIE_OVERIG" 40 0.18 "CONTINUOUS" "1222" "G")
  (list "1225" "KL-OLIE_LEIDING" 40 0.18 "KL-OLIE-SO" "1222" "G")
  (list "1223" "KL-OLIE_AFSLUITER" 40 0.18 "CONTINUOUS" "1222" "G")
  (list "646" "KL-CV_HUISAANSLUITING" 40 0.18 "KL-CV-SO" "645" "G")
  (list "682" "KL-CV_TRANSPORTLEIDING" 40 0.18 "KL-CV-SO" "645" "G")
  (list "680" "KL-CV_PUT" 40 0.18 "CONTINUOUS" "645" "G")
  (list "678" "KL-CV_MANTELBUIS" 40 0.18 "CONTINUOUS" "645" "G")
  (list "1397" "KL-WINDWAARSCHUWINGSSYSTEEM_KABEL" 220 0.18 "CONTINUOUS" "1396" "G")
  (list "1399" "KL-WIM_KABEL" 150 0.18 "KL-WIM-SO" "1398" "G")
  (list "1204" "KL-KOUDENET_TRANSPORTLEIDING" 130 0.18 "KL-KOUDENET-SO" "1183" "G")
  (list "1201" "KL-KOUDENET_MANTELBUIS" 130 0.18 "CONTINUOUS" "1183" "G")
  (list "1184" "KL-KOUDENET_AANSLUITLEIDING" 130 0.18 "KL-KOUDENET-SO" "1183" "G")
  (list "1413" "KL-TRANSMISSIE_KABEL" 80 0.18 "CONTINUOUS" "1412" "G")
  (list "1403" "KL-FILEMELDSYSTEEM_KABEL" 240 0.18 "CONTINUOUS" "1402" "G")
  (list "1218" "KL-MANTELBUIS_STAAL" 7 0.18 "CONTINUOUS" "1215" "G")
  (list "1216" "KL-MANTELBUIS_PE" 7 0.18 "CONTINUOUS" "1215" "G")
  (list "1217" "KL-MANTELBUIS_PVC" 7 0.18 "CONTINUOUS" "1215" "G")
  (list "1405" "KL-MONITORING_KABEL" 120 0.18 "KL-MONITORING-SO" "1404" "G")
  (list "1409" "KL-VRI_KABEL" 30 0.18 "KL-VRI-SO" "1408" "G")
  (list "1393" "KL-GMS_KABEL" 20 0.18 "KL-GMS-SO" "1392" "G")
  (list "1391" "KL-TDI_KABEL" 200 0.18 "KL-TDI-SO" "1390" "G")
  (list "1421" "KL-POMP_KABEL" 230 0.18 "CONTINUOUS" "1420" "G")
  (list "1395" "KL-HOOGTEDETECTIE_KABEL" 190 0.18 "CONTINUOUS" "1394" "G")
  (list "1407" "KL-VS_KABEL" 30 0.18 "KL-VS-SO" "1406" "G")
  (list "622" "KL-BRANDSTOF_HULPSTUK_AANSLUITPUNT" 40 0.18 "CONTINUOUS" "621" "G")
  (list "624" "KL-BRANDSTOF_HULPSTUK_DRUKMEETPUNT" 40 0.18 "CONTINUOUS" "621" "G")
  (list "623" "KL-BRANDSTOF_HULPSTUK_AFSLUITER" 40 0.18 "CONTINUOUS" "621" "G")
  (list "625" "KL-BRANDSTOF_HULPSTUK_ONTLUCHTING" 40 0.18 "CONTINUOUS" "621" "G")
  (list "635" "KL-BRANDSTOF_TRANSPORTLEIDING_STAAL" 40 0.18 "KL-BRANDSTOF-SO" "632" "G")
  (list "633" "KL-BRANDSTOF_TRANSPORTLEIDING_GVK" 40 0.18 "KL-BRANDSTOF-SO" "632" "G")
  (list "634" "KL-BRANDSTOF_TRANSPORTLEIDING_PE" 40 0.18 "KL-BRANDSTOF-SO" "632" "G")
  (list "1254" "KL-WARMTENET_TRANSPORTLEIDING_AANVOER" 80 0.18 "KL-WARMTENET-SO" "1253" "G")
  (list "1259" "KL-WARMTENET_TRANSPORTLEIDING_RETOUR" 80 0.18 "KL-WARMTENET-SO" "1253" "G")
  (list "1234" "KL-WARMTENET_AANSLUITLEIDING_AANVOER" 80 0.18 "KL-WARMTENET-SO" "1233" "G")
  (list "1239" "KL-WARMTENET_AANSLUITLEIDING_RETOUR" 80 0.18 "KL-WARMTENET-SO" "1233" "G")
  (list "1247" "KL-WARMTENET_HULPSTUK_AFSLUITER" 80 0.18 "CONTINUOUS" "1245" "G")
  (list "1246" "KL-WARMTENET_HULPSTUK_AANSLUITPUNT" 80 0.18 "CONTINUOUS" "1245" "G")
  (list "1248" "KL-WARMTENET_HULPSTUK_OVERIG" 80 0.18 "CONTINUOUS" "1245" "G")
  (list "3430" "KL-CCTV_KABEL_VOEDING" 70 0.18 "CONTINUOUS" "1419" "G")
  (list "3432" "KL-CCTV_KABEL_COMBI" 70 0.18 "CONTINUOUS" "1419" "G")
  (list "3431" "KL-CCTV_KABEL_COMMUNICATIE" 70 0.18 "CONTINUOUS" "1419" "G")
  (list "1340" "KL-WATER_HUISAANSLUITING_PVC" 170 0.18 "KL-WATER-SO" "1331" "G")
  (list "1332" "KL-WATER_HUISAANSLUITING_PE" 170 0.18 "KL-WATER-SO" "1331" "G")
  (list "1352" "KL-WATER_HULPSTUK_DRUKREGELAAR" 170 0.18 "CONTINUOUS" "1348" "G")
  (list "1349" "KL-WATER_HULPSTUK_AANSLUITPUNT" 170 0.18 "CONTINUOUS" "1348" "G")
  (list "1350" "KL-WATER_HULPSTUK_AFSLUITER" 170 0.18 "CONTINUOUS" "1348" "G")
  (list "1355" "KL-WATER_HULPSTUK_WATERMETER" 170 0.18 "CONTINUOUS" "1348" "G")
  (list "1351" "KL-WATER_HULPSTUK_DRUKMEETPUNT" 170 0.18 "CONTINUOUS" "1348" "G")
  (list "1354" "KL-WATER_HULPSTUK_SCHOONMAAKSTUK" 170 0.18 "CONTINUOUS" "1348" "G")
  (list "1266" "KL-WATER_BEREGENING_AANSLUITLEIDING" 150 0.18 "KL-WATER-SO" "1265" "G")
  (list "1277" "KL-WATER_BEREGENING_PUT" 150 0.18 "KL-WATER-SO" "1265" "G")
  (list "1276" "KL-WATER_BEREGENING_POMPPUT" 150 0.18 "KL-WATER-SO" "1265" "G")
  (list "1279" "KL-WATER_BEREGENING_TRANSPORTLEIDING" 150 0.18 "KL-WATER-SO" "1265" "G")
  (list "1284" "KL-WATER_BRANDLEIDING_HUISAANSLUITING" 150 0.18 "KL-WATER-SO" "1280" "G")
  (list "1311" "KL-WATER_BRANDLEIDING_PUTKAST" 150 0.18 "CONTINUOUS" "1280" "G")
  (list "1312" "KL-WATER_BRANDLEIDING_TRANSPORTLEIDING" 150 0.18 "KL-WATER-SO" "1280" "G")
  (list "1363" "KL-WATER_PUT_PUTKAST" 170 0.18 "CONTINUOUS" "1361" "G")
  (list "1375" "KL-WATER_TRANSPORTLEIDING_PVC" 170 0.18 "KL-WATER-SO" "1365" "G")
  (list "1366" "KL-WATER_TRANSPORTLEIDING_PE" 170 0.18 "KL-WATER-SO" "1365" "G")
  (list "1177" "KL-GAS_PUT_PUTKAST" 30 0.18 "CONTINUOUS" "1176" "G")
  (list "1054" "KL-GAS_HD_HOOFDLEIDING" 30 0.18 "KL-GAS_HD-SO" "999" "G")
  (list "1000" "KL-GAS_HD_AANSLUITLEIDING" 30 0.18 "KL-GAS_HD-SO" "999" "G")
  (list "1113" "KL-GAS_LD_AANSLUITLEIDING" 50 0.18 "KL-GAS_LD-SO" "1112" "G")
  (list "1143" "KL-GAS_LD_HOOFDLEIDING" 50 0.18 "KL-GAS_LD-SO" "1112" "G")
  (list "1107" "KL-GAS_HULPSTUK_KNOOPPUNT" 30 0.18 "CONTINUOUS" "1102" "G")
  (list "1108" "KL-GAS_HULPSTUK_MOFVERBINDING" 30 0.18 "CONTINUOUS" "1102" "G")
  (list "1105" "KL-GAS_HULPSTUK_DRUKMEETPUNT" 30 0.18 "CONTINUOUS" "1102" "G")
  (list "1106" "KL-GAS_HULPSTUK_FLENSVERBINDING" 30 0.18 "CONTINUOUS" "1102" "G")
  (list "1103" "KL-GAS_HULPSTUK_AANSLUITPUNT" 30 0.18 "CONTINUOUS" "1102" "G")
  (list "1104" "KL-GAS_HULPSTUK_AFSLUITER" 30 0.18 "CONTINUOUS" "1102" "G")
  (list "1179" "KL-GAS_STATION_AFLEVERSTATION" 30 0.18 "CONTINUOUS" "1178" "G")
  (list "1181" "KL-GAS_STATION_HOOFDVERDEELSTATION" 30 0.18 "CONTINUOUS" "1178" "G")
  (list "1182" "KL-GAS_STATION_ONTVANGSTSTATION" 30 0.18 "CONTINUOUS" "1178" "G")
  (list "1180" "KL-GAS_STATION_DISTRICTSTATION" 30 0.18 "CONTINUOUS" "1178" "G")
  (list "3119" "KL-DATA_SIGNAALKABEL_PRORAIL" 90 0.18 "KL-DATA_PRORAIL-SO" "789" "G")
  (list "790" "KL-DATA_SIGNAALKABEL_GLASVEZEL" 90 0.18 "KL-SIGNAALKABEL-SO" "789" "G")
  (list "799" "KL-DATA_SIGNAALKABEL_KOPER" 90 0.18 "KL-SIGNAALKABEL-SO" "789" "G")
  (list "828" "KL-DATA_WAN_GLASVEZEL" 90 0.18 "KL-WAN-SO" "827" "G")
  (list "837" "KL-DATA_WAN_MANTELBUIS" 90 0.18 "CONTINUOUS" "827" "G")
  (list "748" "KL-DATA_DEFENSIE_MANTELBUIS" 90 0.18 "CONTINUOUS" "737" "G")
  (list "747" "KL-DATA_DEFENSIE_KOPER" 90 0.18 "KL-DEF-SO" "737" "G")
  (list "738" "KL-DATA_DEFENSIE_GLASVEZEL" 90 0.18 "KL-DEF-SO" "737" "G")
  (list "811" "KL-DATA_STUURKABEL_KOPER" 90 0.18 "KL-STUURKABEL-SO" "801" "G")
  (list "812" "KL-DATA_STUURKABEL_MANTELBUIS" 90 0.18 "KL-STUURKABEL-SO" "801" "G")
  (list "802" "KL-DATA_STUURKABEL_GLASVEZEL" 90 0.18 "KL-STUURKABEL-SO" "801" "G")
  (list "723" "KL-DATA_ALGEMEEN_KABELNUMMER" 90 0.18 "CONTINUOUS" "722" "G")
  (list "784" "KL-DATA_KAST_PUTKAST" 90 0.18 "CONTINUOUS" "782" "G")
  (list "785" "KL-DATA_KAST_VERDEELKAST" 90 0.18 "CONTINUOUS" "782" "G")
  (list "783" "KL-DATA_KAST_LASKAST" 90 0.18 "CONTINUOUS" "782" "G")
  (list "824" "KL-DATA_TELECOM_KOPER" 90 0.18 "KL-TELECOM-SO" "814" "G")
  (list "815" "KL-DATA_TELECOM_GLASVEZEL" 90 0.18 "KL-TELECOM-SO" "814" "G")
  (list "825" "KL-DATA_TELECOM_MANTELBUIS" 90 0.18 "CONTINUOUS" "814" "G")
  (list "2986" "KL-DATA_GLASVEZEL_KABELBUIS" 90 0.18 "CONTINUOUS" "750" "G")
  (list "2984" "KL-DATA_GLASVEZEL_BORING" 7 0.18 "ZZ-CENTER-SO" "750" "G")
  (list "759" "KL-DATA_GLASVEZEL_MANTELBUIS" 90 0.18 "CONTINUOUS" "750" "G")
  (list "775" "KL-DATA_INTERCOM_KOPER" 90 0.18 "KL-TELECOM-SO" "765" "G")
  (list "766" "KL-DATA_INTERCOM_GLASVEZEL" 90 0.18 "KL-TELECOM-SO" "765" "G")
  (list "776" "KL-DATA_INTERCOM_MANTELBUIS" 90 0.18 "CONTINUOUS" "765" "G")
  (list "733" "KL-DATA_CAI_KOPER" 90 0.18 "KL-CAI-SO" "724" "G")
  (list "735" "KL-DATA_CAI_MANTELBUIS" 90 0.18 "CONTINUOUS" "724" "G")
  (list "763" "KL-DATA_HULPSTUK_MOF" 90 0.18 "CONTINUOUS" "761" "G")
  (list "762" "KL-DATA_HULPSTUK_AANSLUITPUNT" 90 0.18 "CONTINUOUS" "761" "G")
  (list "2959" "KL-SCHEMA_RASTERINDELING_18" 7 0.18 "CONTINUOUS" "2958" "G")
  (list "2961" "KL-SCHEMA_RASTERINDELING_35" 7 0.35 "CONTINUOUS" "2958" "G")
  (list "2960" "KL-SCHEMA_RASTERINDELING_25" 7 0.25 "CONTINUOUS" "2958" "G")
  (list "975" "KL-ET_MS_10 kV" 130 0.18 "KL-MS-SO" "973" "G")
  (list "974" "KL-ET_MS_04 kV" 130 0.18 "KL-MS-SO" "973" "G")
  (list "976" "KL-ET_MS_30 kV" 130 0.18 "KL-MS-SO" "973" "G")
  (list "982" "KL-ET_MS_MANTELBUIS" 130 0.18 "CONTINUOUS" "973" "G")
  (list "960" "KL-ET_LS_VOEDINGKAST" 190 0.18 "CONTINUOUS" "878" "G")
  (list "885" "KL-ET_LS_MANTELBUIS" 190 0.18 "CONTINUOUS" "878" "G")
  (list "883" "KL-ET_LS_KABELBUNDEL" 190 0.18 "KL-BUNDEL-SO" "878" "G")
  (list "959" "KL-ET_LS_VERDEELKAST" 190 0.18 "CONTINUOUS" "878" "G")
  (list "918" "KL-ET_LS_SR" 190 0.18 "KL-LS-SO" "878" "G")
  (list "961" "KL-ET_LS_VOEDINGSKABEL" 190 0.18 "KL-LS-SO" "878" "G")
  (list "917" "KL-ET_LS_PUTKAST" 190 0.18 "CONTINUOUS" "878" "G")
  (list "3504" "KL-ET_HS_HOOGSPANNINGSMAST" 10 0.18 "CONTINUOUS" "863" "G")
  (list "865" "KL-ET_HS_36 kV" 10 0.18 "KL-HS-SO" "863" "G")
  (list "871" "KL-ET_HS_MANTELBUIS" 10 0.18 "CONTINUOUS" "863" "G")
  (list "864" "KL-ET_HS_220 kV" 10 0.18 "KL-HS-SO" "863" "G")
  (list "994" "KL-ET_ZHS_MANTELBUIS" 10 0.18 "CONTINUOUS" "986" "G")
  (list "995" "KL-ET_ZHS_HOOGSPANNINGSMAST" 10 0.18 "CONTINUOUS" "986" "G")
  (list "988" "KL-ET_ZHS_380 kV" 10 0.18 "KL-ZHS-SO" "986" "G")
  (list "987" "KL-ET_ZHS_110 kV" 10 0.18 "KL-ZHS-SO" "986" "G")
  (list "853" "KL-ET_AARDING_KABEL" 7 0.18 "KL-AARDING-SO" "841" "G")
  (list "842" "KL-ET_AARDING_AARDELECTRODE" 7 0.18 "CONTINUOUS" "841" "G")
  (list "844" "KL-ET_AARDING_BLIKSEMAFLEIDER" 7 0.18 "CONTINUOUS" "841" "G")
  (list "848" "KL-ET_AARDING_HULPSTUK" 7 0.18 "CONTINUOUS" "841" "G")
  (list "860" "KL-ET_AARDING_MEETPUNT" 7 0.18 "CONTINUOUS" "841" "G")
  (list "859" "KL-ET_AARDING_MANTELBUIS" 7 0.18 "CONTINUOUS" "841" "G")
  (list "843" "KL-ET_AARDING_AARDRAIL" 7 0.18 "CONTINUOUS" "841" "G")
  (list "876" "KL-ET_HULPSTUK_MOF" 10 0.18 "CONTINUOUS" "874" "G")
  (list "875" "KL-ET_HULPSTUK_AANSLUITPUNT" 10 0.18 "CONTINUOUS" "874" "G")
  (list "971" "KL-ET_MANTELBUIS_PVC" 10 0.18 "CONTINUOUS" "969" "G")
  (list "972" "KL-ET_MANTELBUIS_STAAL" 10 0.18 "CONTINUOUS" "969" "G")
  (list "970" "KL-ET_MANTELBUIS_PE" 10 0.18 "CONTINUOUS" "969" "G")
  (list "654" "KL-CV_HUISAANSLUITING_STAAL" 40 0.18 "KL-CV-SO" "646" "G")
  (list "647" "KL-CV_HUISAANSLUITING_GVK" 40 0.18 "KL-CV-SO" "646" "G")
  (list "675" "KL-CV_HULPSTUK_AFSLUITER" 40 0.18 "CONTINUOUS" "673" "G")
  (list "674" "KL-CV_HULPSTUK_AANSLUITPUNT" 40 0.18 "CONTINUOUS" "673" "G")
  (list "701" "KL-CV_TRANSPORTLEIDING_STAAL" 40 0.18 "KL-CV-SO" "682" "G")
  (list "683" "KL-CV_TRANSPORTLEIDING_GVK" 40 0.18 "KL-CV-SO" "682" "G")
  (list "681" "KL-CV_PUT_PUTKAST" 40 0.18 "CONTINUOUS" "680" "G")
  (list "1210" "KL-KOUDENET_TRANSPORTLEIDING_RETOUR" 130 0.18 "KL-KOUDENET-SO" "1204" "G")
  (list "1205" "KL-KOUDENET_TRANSPORTLEIDING_AANVOER" 130 0.18 "KL-KOUDENET-SO" "1204" "G")
  (list "1198" "KL-KOUDENET_HULPSTUK_AFSLUITER" 130 0.18 "CONTINUOUS" "1196" "G")
  (list "1197" "KL-KOUDENET_HULPSTUK_AANSLUITPUNT" 130 0.18 "CONTINUOUS" "1196" "G")
  (list "1190" "KL-KOUDENET_AANSLUITLEIDING_RETOUR" 130 0.18 "KL-KOUDENET-SO" "1184" "G")
  (list "1185" "KL-KOUDENET_AANSLUITLEIDING_AANVOER" 130 0.18 "KL-KOUDENET-SO" "1184" "G")
  (list "1257" "KL-WARMTENET_TRANSPORTLEIDING_AANVOER_PVC" 80 0.18 "KL-WARMTENET-SO" "1254" "G")
  (list "1256" "KL-WARMTENET_TRANSPORTLEIDING_AANVOER_PE" 80 0.18 "KL-WARMTENET-SO" "1254" "G")
  (list "1258" "KL-WARMTENET_TRANSPORTLEIDING_AANVOER_STAAL" 80 0.18 "KL-WARMTENET-SO" "1254" "G")
  (list "1255" "KL-WARMTENET_TRANSPORTLEIDING_AANVOER_GVK" 80 0.18 "KL-WARMTENET-SO" "1254" "G")
  (list "1261" "KL-WARMTENET_TRANSPORTLEIDING_RETOUR_PE" 80 0.18 "KL-WARMTENET-SO" "1259" "G")
  (list "1262" "KL-WARMTENET_TRANSPORTLEIDING_RETOUR_PVC" 80 0.18 "KL-WARMTENET-SO" "1259" "G")
  (list "1263" "KL-WARMTENET_TRANSPORTLEIDING_RETOUR_STAAL" 80 0.18 "KL-WARMTENET-SO" "1259" "G")
  (list "1260" "KL-WARMTENET_TRANSPORTLEIDING_RETOUR_GVK" 80 0.18 "KL-WARMTENET-SO" "1259" "G")
  (list "1236" "KL-WARMTENET_AANSLUITLEIDING_AANVOER_PE" 80 0.18 "KL-WARMTENET-SO" "1234" "G")
  (list "1238" "KL-WARMTENET_AANSLUITLEIDING_AANVOER_STAAL" 80 0.18 "KL-WARMTENET-SO" "1234" "G")
  (list "1235" "KL-WARMTENET_AANSLUITLEIDING_AANVOER_GVK" 80 0.18 "KL-WARMTENET-SO" "1234" "G")
  (list "1237" "KL-WARMTENET_AANSLUITLEIDING_AANVOER_PVC" 80 0.18 "KL-WARMTENET-SO" "1234" "G")
  (list "1241" "KL-WARMTENET_AANSLUITLEIDING_RETOUR_PE" 80 0.18 "KL-WARMTENET-SO" "1239" "G")
  (list "1243" "KL-WARMTENET_AANSLUITLEIDING_RETOUR_STAAL" 80 0.18 "KL-WARMTENET-SO" "1239" "G")
  (list "1240" "KL-WARMTENET_AANSLUITLEIDING_RETOUR_GVK" 80 0.18 "KL-WARMTENET-SO" "1239" "G")
  (list "1242" "KL-WARMTENET_AANSLUITLEIDING_RETOUR_PVC" 80 0.18 "KL-WARMTENET-SO" "1239" "G")
  (list "1347" "KL-WATER_HUISAANSLUITING_PVC_90" 170 0.18 "KL-WATER-SO" "1340" "G")
  (list "1342" "KL-WATER_HUISAANSLUITING_PVC_32" 170 0.18 "KL-WATER-SO" "1340" "G")
  (list "1341" "KL-WATER_HUISAANSLUITING_PVC_110" 170 0.18 "KL-WATER-SO" "1340" "G")
  (list "1345" "KL-WATER_HUISAANSLUITING_PVC_63" 170 0.18 "KL-WATER-SO" "1340" "G")
  (list "1343" "KL-WATER_HUISAANSLUITING_PVC_40" 170 0.18 "KL-WATER-SO" "1340" "G")
  (list "1344" "KL-WATER_HUISAANSLUITING_PVC_50" 170 0.18 "KL-WATER-SO" "1340" "G")
  (list "1346" "KL-WATER_HUISAANSLUITING_PVC_75" 170 0.18 "KL-WATER-SO" "1340" "G")
  (list "1333" "KL-WATER_HUISAANSLUITING_PE_110" 170 0.18 "KL-WATER-SO" "1332" "G")
  (list "1338" "KL-WATER_HUISAANSLUITING_PE_75" 170 0.18 "KL-WATER-SO" "1332" "G")
  (list "1339" "KL-WATER_HUISAANSLUITING_PE_90" 170 0.18 "KL-WATER-SO" "1332" "G")
  (list "1335" "KL-WATER_HUISAANSLUITING_PE_40" 170 0.18 "KL-WATER-SO" "1332" "G")
  (list "1334" "KL-WATER_HUISAANSLUITING_PE_32" 170 0.18 "KL-WATER-SO" "1332" "G")
  (list "1337" "KL-WATER_HUISAANSLUITING_PE_63" 170 0.18 "KL-WATER-SO" "1332" "G")
  (list "1336" "KL-WATER_HUISAANSLUITING_PE_50" 170 0.18 "KL-WATER-SO" "1332" "G")
  (list "1269" "KL-WATER_BEREGENING_HULPSTUK_AFSLUITER" 153 0.18 "CONTINUOUS" "1267" "G")
  (list "1273" "KL-WATER_BEREGENING_HULPSTUK_SCHOONMAAKSTUK" 153 0.18 "CONTINUOUS" "1267" "G")
  (list "1270" "KL-WATER_BEREGENING_HULPSTUK_DRUKMEETPUNT" 153 0.18 "CONTINUOUS" "1267" "G")
  (list "1274" "KL-WATER_BEREGENING_HULPSTUK_WATERMETER" 153 0.18 "CONTINUOUS" "1267" "G")
  (list "1271" "KL-WATER_BEREGENING_HULPSTUK_DRUKREGELAAR" 153 0.18 "CONTINUOUS" "1267" "G")
  (list "1268" "KL-WATER_BEREGENING_HULPSTUK_AANSLUITPUNT" 153 0.18 "CONTINUOUS" "1267" "G")
  (list "1293" "KL-WATER_BRANDLEIDING_HUISAANSLUITING_PVC" 150 0.18 "KL-WATER-SO" "1284" "G")
  (list "1285" "KL-WATER_BRANDLEIDING_HUISAANSLUITING_PE" 150 0.18 "KL-WATER-SO" "1284" "G")
  (list "1305" "KL-WATER_BRANDLEIDING_HULPSTUK_DRUKREGELAAR" 150 0.18 "CONTINUOUS" "1301" "G")
  (list "1307" "KL-WATER_BRANDLEIDING_HULPSTUK_SCHOONMAAKSTUK" 150 0.18 "CONTINUOUS" "1301" "G")
  (list "1303" "KL-WATER_BRANDLEIDING_HULPSTUK_AFSLUITER" 150 0.18 "CONTINUOUS" "1301" "G")
  (list "1304" "KL-WATER_BRANDLEIDING_HULPSTUK_DRUKMEETPUNT" 150 0.18 "CONTINUOUS" "1301" "G")
  (list "1308" "KL-WATER_BRANDLEIDING_HULPSTUK_WATERMETER" 150 0.18 "CONTINUOUS" "1301" "G")
  (list "1302" "KL-WATER_BRANDLEIDING_HULPSTUK_AANSLUITPUNT" 150 0.18 "CONTINUOUS" "1301" "G")
  (list "1282" "KL-WATER_BRANDLEIDING_BRANDHYDRANT_BOVENGRONDS" 150 0.18 "CONTINUOUS" "1281" "G")
  (list "1283" "KL-WATER_BRANDLEIDING_BRANDHYDRANT_ONDERGRONDS" 150 0.18 "CONTINUOUS" "1281" "G")
  (list "1313" "KL-WATER_BRANDLEIDING_TRANSPORTLEIDING_PE" 150 0.18 "KL-WATER-SO" "1312" "G")
  (list "1322" "KL-WATER_BRANDLEIDING_TRANSPORTLEIDING_PVC" 150 0.18 "KL-WATER-SO" "1312" "G")
  (list "1380" "KL-WATER_TRANSPORTLEIDING_PVC_315" 170 0.18 "KL-WATER-SO" "1375" "G")
  (list "1376" "KL-WATER_TRANSPORTLEIDING_PVC_110" 170 0.18 "KL-WATER-SO" "1375" "G")
  (list "1378" "KL-WATER_TRANSPORTLEIDING_PVC_160" 170 0.18 "KL-WATER-SO" "1375" "G")
  (list "1383" "KL-WATER_TRANSPORTLEIDING_PVC_630" 170 0.18 "KL-WATER-SO" "1375" "G")
  (list "1381" "KL-WATER_TRANSPORTLEIDING_PVC_400" 170 0.18 "KL-WATER-SO" "1375" "G")
  (list "1377" "KL-WATER_TRANSPORTLEIDING_PVC_125" 170 0.18 "KL-WATER-SO" "1375" "G")
  (list "1382" "KL-WATER_TRANSPORTLEIDING_PVC_500" 170 0.18 "KL-WATER-SO" "1375" "G")
  (list "1379" "KL-WATER_TRANSPORTLEIDING_PVC_250" 170 0.18 "KL-WATER-SO" "1375" "G")
  (list "1371" "KL-WATER_TRANSPORTLEIDING_PE_315" 170 0.18 "KL-WATER-SO" "1366" "G")
  (list "1372" "KL-WATER_TRANSPORTLEIDING_PE_400" 170 0.18 "KL-WATER-SO" "1366" "G")
  (list "1373" "KL-WATER_TRANSPORTLEIDING_PE_500" 170 0.18 "KL-WATER-SO" "1366" "G")
  (list "1370" "KL-WATER_TRANSPORTLEIDING_PE_250" 170 0.18 "KL-WATER-SO" "1366" "G")
  (list "1368" "KL-WATER_TRANSPORTLEIDING_PE_125" 170 0.18 "KL-WATER-SO" "1366" "G")
  (list "1369" "KL-WATER_TRANSPORTLEIDING_PE_160" 170 0.18 "KL-WATER-SO" "1366" "G")
  (list "1374" "KL-WATER_TRANSPORTLEIDING_PE_630" 170 0.18 "KL-WATER-SO" "1366" "G")
  (list "1367" "KL-WATER_TRANSPORTLEIDING_PE_110" 170 0.18 "KL-WATER-SO" "1366" "G")
  (list "1055" "KL-GAS_HD_HOOFDLEIDING_1 BAR" 30 0.18 "KL-GAS_HD-SO" "1054" "G")
  (list "1085" "KL-GAS_HD_HOOFDLEIDING_40 BAR" 30 0.18 "KL-GAS_HD-SO" "1054" "G")
  (list "1070" "KL-GAS_HD_HOOFDLEIDING_4 BAR" 30 0.18 "KL-GAS_HD-SO" "1054" "G")
  (list "1087" "KL-GAS_HD_HOOFDLEIDING_8 BAR" 30 0.18 "KL-GAS_HD-SO" "1054" "G")
  (list "1086" "KL-GAS_HD_HOOFDLEIDING_67 BAR" 30 0.18 "KL-GAS_HD-SO" "1054" "G")
  (list "1037" "KL-GAS_HD_AANSLUITLEIDING_8 BAR" 30 0.18 "KL-GAS_HD-SO" "1000" "G")
  (list "1036" "KL-GAS_HD_AANSLUITLEIDING_67 BAR" 30 0.18 "KL-GAS_HD-SO" "1000" "G")
  (list "1018" "KL-GAS_HD_AANSLUITLEIDING_4 BAR" 30 0.18 "KL-GAS_HD-SO" "1000" "G")
  (list "1001" "KL-GAS_HD_AANSLUITLEIDING_1 BAR" 30 0.18 "KL-GAS_HD-SO" "1000" "G")
  (list "1035" "KL-GAS_HD_AANSLUITLEIDING_40 BAR" 30 0.18 "KL-GAS_HD-SO" "1000" "G")
  (list "1114" "KL-GAS_LD_AANSLUITLEIDING_100 MBAR" 50 0.18 "KL-GAS_LD-SO" "1113" "G")
  (list "1129" "KL-GAS_LD_AANSLUITLEIDING_30 MBAR" 50 0.18 "KL-GAS_LD-SO" "1113" "G")
  (list "1144" "KL-GAS_LD_HOOFDLEIDING_100 MBAR" 50 0.18 "KL-GAS_LD-SO" "1143" "G")
  (list "1159" "KL-GAS_LD_HOOFDLEIDING_30 MBAR" 50 0.18 "KL-GAS_LD-SO" "1143" "G")
  (list "793" "KL-DATA_SIGNAALKABEL_HULPSTUK_MOF" 90 0.18 "CONTINUOUS" "791" "G")
  (list "792" "KL-DATA_SIGNAALKABEL_HULPSTUK_AANSLUITPUNT" 90 0.18 "CONTINUOUS" "791" "G")
  (list "797" "KL-DATA_SIGNAALKABEL_KAST_PUTKAST" 90 0.18 "KL-SIGNAALKABEL-SO" "795" "G")
  (list "798" "KL-DATA_SIGNAALKABEL_KAST_VERDEELKAST" 90 0.18 "KL-SIGNAALKABEL-SO" "795" "G")
  (list "796" "KL-DATA_SIGNAALKABEL_KAST_LASKAST" 90 0.18 "KL-SIGNAALKABEL-SO" "795" "G")
  (list "834" "KL-DATA_WAN_KAST_LASKAST" 90 0.18 "CONTINUOUS" "833" "G")
  (list "836" "KL-DATA_WAN_KAST_VERDEELKAST" 90 0.18 "CONTINUOUS" "833" "G")
  (list "835" "KL-DATA_WAN_KAST_PUTKAST" 90 0.18 "CONTINUOUS" "833" "G")
  (list "831" "KL-DATA_WAN_HULPSTUK_MOF" 90 0.18 "CONTINUOUS" "829" "G")
  (list "830" "KL-DATA_WAN_HULPSTUK_AANSLUITPUNT" 90 0.18 "CONTINUOUS" "829" "G")
  (list "741" "KL-DATA_DEFENSIE_HULPSTUK_MOF" 90 0.18 "CONTINUOUS" "739" "G")
  (list "742" "KL-DATA_DEFENSIE_HULPSTUK_OVERIG" 90 0.18 "CONTINUOUS" "739" "G")
  (list "740" "KL-DATA_DEFENSIE_HULPSTUK_AANSLUITPUNT" 90 0.18 "CONTINUOUS" "739" "G")
  (list "746" "KL-DATA_DEFENSIE_KAST_VERDEELKAST" 90 0.18 "CONTINUOUS" "743" "G")
  (list "744" "KL-DATA_DEFENSIE_KAST_LASKAST" 90 0.18 "CONTINUOUS" "743" "G")
  (list "745" "KL-DATA_DEFENSIE_KAST_PUTKAST" 90 0.18 "CONTINUOUS" "743" "G")
  (list "809" "KL-DATA_STUURKABEL_KAST_PUTKAST" 90 0.18 "KL-STUURKABEL-SO" "807" "G")
  (list "808" "KL-DATA_STUURKABEL_KAST_LASKAST" 90 0.18 "KL-STUURKABEL-SO" "807" "G")
  (list "810" "KL-DATA_STUURKABEL_KAST_VERDEELKAST" 90 0.18 "KL-STUURKABEL-SO" "807" "G")
  (list "805" "KL-DATA_STUURKABEL_HULPSTUK_MOF" 90 0.18 "CONTINUOUS" "803" "G")
  (list "804" "KL-DATA_STUURKABEL_HULPSTUK_AANSLUITPUNT" 90 0.18 "CONTINUOUS" "803" "G")
  (list "818" "KL-DATA_TELECOM_HULPSTUK_MOF" 90 0.18 "CONTINUOUS" "816" "G")
  (list "817" "KL-DATA_TELECOM_HULPSTUK_AANSLUITPUNT" 90 0.18 "CONTINUOUS" "816" "G")
  (list "822" "KL-DATA_TELECOM_KAST_PUTKAST" 90 0.18 "CONTINUOUS" "820" "G")
  (list "823" "KL-DATA_TELECOM_KAST_VERDEELKAST" 90 0.18 "CONTINUOUS" "820" "G")
  (list "821" "KL-DATA_TELECOM_KAST_LASKAST" 90 0.18 "CONTINUOUS" "820" "G")
  (list "2987" "KL-DATA_GLASVEZEL_KABELBUIS_SUBDUCT" 90 0.18 "CONTINUOUS" "2986" "G")
  (list "758" "KL-DATA_GLASVEZEL_KAST_VERDEELKAST" 90 0.18 "CONTINUOUS" "755" "G")
  (list "756" "KL-DATA_GLASVEZEL_KAST_LASKAST" 90 0.18 "CONTINUOUS" "755" "G")
  (list "757" "KL-DATA_GLASVEZEL_KAST_PUTKAST" 90 0.18 "CONTINUOUS" "755" "G")
  (list "2985" "KL-DATA_GLASVEZEL_BORING_GESTUURD" 7 0.18 "CONTINUOUS" "2984" "G")
  (list "752" "KL-DATA_GLASVEZEL_HULPSTUK_AANSLUITPUNT" 90 0.18 "CONTINUOUS" "751" "G")
  (list "753" "KL-DATA_GLASVEZEL_HULPSTUK_MOF" 90 0.18 "CONTINUOUS" "751" "G")
  (list "768" "KL-DATA_INTERCOM_HULPSTUK_AANSLUITPUNT" 90 0.18 "CONTINUOUS" "767" "G")
  (list "769" "KL-DATA_INTERCOM_HULPSTUK_MOF" 90 0.18 "CONTINUOUS" "767" "G")
  (list "772" "KL-DATA_INTERCOM_KAST_LASKAST" 90 0.18 "CONTINUOUS" "771" "G")
  (list "774" "KL-DATA_INTERCOM_KAST_VERDEELKAST" 90 0.18 "CONTINUOUS" "771" "G")
  (list "773" "KL-DATA_INTERCOM_KAST_PUTKAST" 90 0.18 "CONTINUOUS" "771" "G")
  (list "732" "KL-DATA_CAI_KAST_VERDEELKAST" 90 0.18 "CONTINUOUS" "729" "G")
  (list "731" "KL-DATA_CAI_KAST_PUTKAST" 90 0.18 "CONTINUOUS" "729" "G")
  (list "730" "KL-DATA_CAI_KAST_LASKAST" 90 0.18 "CONTINUOUS" "729" "G")
  (list "734" "KL-DATA_CAI_KOPER_COAX3" 90 0.18 "KL-CAI-SO" "733" "G")
  (list "727" "KL-DATA_CAI_HULPSTUK_MOF" 90 0.18 "CONTINUOUS" "725" "G")
  (list "726" "KL-DATA_CAI_HULPSTUK_AANSLUITPUNT" 90 0.18 "CONTINUOUS" "725" "G")
  (list "979" "KL-ET_MS_HULPSTUK_MOF" 130 0.18 "CONTINUOUS" "977" "G")
  (list "978" "KL-ET_MS_HULPSTUK_AANSLUITPUNT" 130 0.18 "CONTINUOUS" "977" "G")
  (list "880" "KL-ET_LS_HULPSTUK_AANSLUITPUNT" 190 0.18 "CONTINUOUS" "879" "G")
  (list "881" "KL-ET_LS_HULPSTUK_MOF" 190 0.18 "CONTINUOUS" "879" "G")
  (list "919" "KL-ET_LS_SR_ARMATUUR" 190 0.18 "CONTINUOUS" "918" "G")
  (list "957" "KL-ET_LS_SR_PUT" 190 0.18 "CONTINUOUS" "918" "G")
  (list "944" "KL-ET_LS_SR_BORD" 190 0.18 "CONTINUOUS" "918" "G")
  (list "955" "KL-ET_LS_SR_MANTELBUIS" 190 0.18 "CONTINUOUS" "918" "G")
  (list "958" "KL-ET_LS_SR_TRAFO" 190 0.18 "CONTINUOUS" "918" "G")
  (list "949" "KL-ET_LS_SR_HULPSTUK" 190 0.18 "CONTINUOUS" "918" "G")
  (list "967" "KL-ET_LS_VOEDINGSKABEL_POORT" 190 0.18 "CONTINUOUS" "961" "G")
  (list "963" "KL-ET_LS_VOEDINGSKABEL_GEBOUW" 190 0.18 "CONTINUOUS" "961" "G")
  (list "966" "KL-ET_LS_VOEDINGSKABEL_POMP" 190 0.18 "CONTINUOUS" "961" "G")
  (list "962" "KL-ET_LS_VOEDINGSKABEL_AGGREGAAT" 190 0.18 "CONTINUOUS" "961" "G")
  (list "867" "KL-ET_HS_HULPSTUK_AANSLUITPUNT" 10 0.18 "CONTINUOUS" "866" "G")
  (list "868" "KL-ET_HS_HULPSTUK_MOF" 10 0.18 "CONTINUOUS" "866" "G")
  (list "991" "KL-ET_ZHS_HULPSTUK_MOF" 10 0.18 "CONTINUOUS" "989" "G")
  (list "990" "KL-ET_ZHS_HULPSTUK_AANSLUITPUNT" 10 0.18 "CONTINUOUS" "989" "G")
  (list "856" "KL-ET_AARDING_KABEL_VEILIGHEIDSKABEL" 7 0.18 "KL-AARDING-SO" "853" "G")
  (list "855" "KL-ET_AARDING_KABEL_POTENTIAALKABEL" 7 0.18 "KL-AARDING-SO" "853" "G")
  (list "854" "KL-ET_AARDING_KABEL_BLIKSEMAFLEIDINGSKABEL" 7 0.18 "KL-AARDING-SO" "853" "G")
  (list "845" "KL-ET_AARDING_BLIKSEMAFLEIDER_AFSPANDRAAD" 7 0.18 "CONTINUOUS" "844" "G")
  (list "846" "KL-ET_AARDING_BLIKSEMAFLEIDER_STIJGPUNT" 7 0.18 "CONTINUOUS" "844" "G")
  (list "847" "KL-ET_AARDING_BLIKSEMAFLEIDER_VANGMAST" 7 0.18 "CONTINUOUS" "844" "G")
  (list "851" "KL-ET_AARDING_HULPSTUK_MOF" 7 0.18 "CONTINUOUS" "848" "G")
  (list "849" "KL-ET_AARDING_HULPSTUK_AANSLUITPUNT" 7 0.18 "CONTINUOUS" "848" "G")
  (list "850" "KL-ET_AARDING_HULPSTUK_AARDTEGEL" 7 0.18 "CONTINUOUS" "848" "G")
  (list "858" "KL-ET_AARDING_KAST_VERDEELKAST" 7 0.18 "CONTINUOUS" "857" "G")
  (list "661" "KL-CV_HUISAANSLUITING_STAAL_DN250" 40 0.18 "KL-CV-SO" "654" "G")
  (list "664" "KL-CV_HUISAANSLUITING_STAAL_DN350" 40 0.18 "KL-CV-SO" "654" "G")
  (list "667" "KL-CV_HUISAANSLUITING_STAAL_DN450" 40 0.18 "KL-CV-SO" "654" "G")
  (list "668" "KL-CV_HUISAANSLUITING_STAAL_DN50" 40 0.18 "KL-CV-SO" "654" "G")
  (list "659" "KL-CV_HUISAANSLUITING_STAAL_DN200" 40 0.18 "KL-CV-SO" "654" "G")
  (list "655" "KL-CV_HUISAANSLUITING_STAAL_DN100" 40 0.18 "KL-CV-SO" "654" "G")
  (list "656" "KL-CV_HUISAANSLUITING_STAAL_DN125" 40 0.18 "KL-CV-SO" "654" "G")
  (list "662" "KL-CV_HUISAANSLUITING_STAAL_DN300" 40 0.18 "KL-CV-SO" "654" "G")
  (list "670" "KL-CV_HUISAANSLUITING_STAAL_DN600" 40 0.18 "KL-CV-SO" "654" "G")
  (list "663" "KL-CV_HUISAANSLUITING_STAAL_DN32" 40 0.18 "KL-CV-SO" "654" "G")
  (list "669" "KL-CV_HUISAANSLUITING_STAAL_DN500" 40 0.18 "KL-CV-SO" "654" "G")
  (list "665" "KL-CV_HUISAANSLUITING_STAAL_DN40" 40 0.18 "KL-CV-SO" "654" "G")
  (list "658" "KL-CV_HUISAANSLUITING_STAAL_DN20" 40 0.18 "KL-CV-SO" "654" "G")
  (list "672" "KL-CV_HUISAANSLUITING_STAAL_DN80" 40 0.18 "KL-CV-SO" "654" "G")
  (list "671" "KL-CV_HUISAANSLUITING_STAAL_DN65" 40 0.18 "KL-CV-SO" "654" "G")
  (list "660" "KL-CV_HUISAANSLUITING_STAAL_DN25" 40 0.18 "KL-CV-SO" "654" "G")
  (list "657" "KL-CV_HUISAANSLUITING_STAAL_DN150" 40 0.18 "KL-CV-SO" "654" "G")
  (list "666" "KL-CV_HUISAANSLUITING_STAAL_DN400" 40 0.18 "KL-CV-SO" "654" "G")
  (list "650" "KL-CV_HUISAANSLUITING_GVK_25" 40 0.18 "KL-CV-SO" "647" "G")
  (list "648" "KL-CV_HUISAANSLUITING_GVK_100" 40 0.18 "KL-CV-SO" "647" "G")
  (list "649" "KL-CV_HUISAANSLUITING_GVK_150" 40 0.18 "KL-CV-SO" "647" "G")
  (list "652" "KL-CV_HUISAANSLUITING_GVK_50" 40 0.18 "KL-CV-SO" "647" "G")
  (list "651" "KL-CV_HUISAANSLUITING_GVK_40" 40 0.18 "KL-CV-SO" "647" "G")
  (list "653" "KL-CV_HUISAANSLUITING_GVK_80" 40 0.18 "KL-CV-SO" "647" "G")
  (list "705" "KL-CV_TRANSPORTLEIDING_STAAL_DN20" 40 0.18 "KL-CV-SO" "701" "G")
  (list "717" "KL-CV_TRANSPORTLEIDING_STAAL_DN600" 40 0.18 "KL-CV-SO" "701" "G")
  (list "702" "KL-CV_TRANSPORTLEIDING_STAAL_DN100" 40 0.18 "KL-CV-SO" "701" "G")
  (list "710" "KL-CV_TRANSPORTLEIDING_STAAL_DN32" 40 0.18 "KL-CV-SO" "701" "G")
  (list "712" "KL-CV_TRANSPORTLEIDING_STAAL_DN40" 40 0.18 "KL-CV-SO" "701" "G")
  (list "704" "KL-CV_TRANSPORTLEIDING_STAAL_DN150" 40 0.18 "KL-CV-SO" "701" "G")
  (list "708" "KL-CV_TRANSPORTLEIDING_STAAL_DN250" 40 0.18 "KL-CV-SO" "701" "G")
  (list "706" "KL-CV_TRANSPORTLEIDING_STAAL_DN200" 40 0.18 "KL-CV-SO" "701" "G")
  (list "703" "KL-CV_TRANSPORTLEIDING_STAAL_DN125" 40 0.18 "KL-CV-SO" "701" "G")
  (list "718" "KL-CV_TRANSPORTLEIDING_STAAL_DN65" 40 0.18 "KL-CV-SO" "701" "G")
  (list "713" "KL-CV_TRANSPORTLEIDING_STAAL_DN400" 40 0.18 "KL-CV-SO" "701" "G")
  (list "707" "KL-CV_TRANSPORTLEIDING_STAAL_DN25" 40 0.18 "KL-CV-SO" "701" "G")
  (list "709" "KL-CV_TRANSPORTLEIDING_STAAL_DN300" 40 0.18 "KL-CV-SO" "701" "G")
  (list "719" "KL-CV_TRANSPORTLEIDING_STAAL_DN80" 40 0.18 "KL-CV-SO" "701" "G")
  (list "711" "KL-CV_TRANSPORTLEIDING_STAAL_DN350" 40 0.18 "KL-CV-SO" "701" "G")
  (list "716" "KL-CV_TRANSPORTLEIDING_STAAL_DN500" 40 0.18 "KL-CV-SO" "701" "G")
  (list "715" "KL-CV_TRANSPORTLEIDING_STAAL_DN50" 40 0.18 "KL-CV-SO" "701" "G")
  (list "714" "KL-CV_TRANSPORTLEIDING_STAAL_DN450" 40 0.18 "KL-CV-SO" "701" "G")
  (list "689" "KL-CV_TRANSPORTLEIDING_GVK_200" 40 0.18 "KL-CV-SO" "683" "G")
  (list "694" "KL-CV_TRANSPORTLEIDING_GVK_450" 40 0.18 "KL-CV-SO" "683" "G")
  (list "696" "KL-CV_TRANSPORTLEIDING_GVK_600" 40 0.18 "KL-CV-SO" "683" "G")
  (list "685" "KL-CV_TRANSPORTLEIDING_GVK_1000" 40 0.18 "KL-CV-SO" "683" "G")
  (list "695" "KL-CV_TRANSPORTLEIDING_GVK_500" 40 0.18 "KL-CV-SO" "683" "G")
  (list "700" "KL-CV_TRANSPORTLEIDING_GVK_900" 40 0.18 "KL-CV-SO" "683" "G")
  (list "684" "KL-CV_TRANSPORTLEIDING_GVK_100" 40 0.18 "KL-CV-SO" "683" "G")
  (list "690" "KL-CV_TRANSPORTLEIDING_GVK_250" 40 0.18 "KL-CV-SO" "683" "G")
  (list "687" "KL-CV_TRANSPORTLEIDING_GVK_1400" 40 0.18 "KL-CV-SO" "683" "G")
  (list "697" "KL-CV_TRANSPORTLEIDING_GVK_700" 40 0.18 "KL-CV-SO" "683" "G")
  (list "686" "KL-CV_TRANSPORTLEIDING_GVK_1200" 40 0.18 "KL-CV-SO" "683" "G")
  (list "698" "KL-CV_TRANSPORTLEIDING_GVK_750" 40 0.18 "KL-CV-SO" "683" "G")
  (list "693" "KL-CV_TRANSPORTLEIDING_GVK_400" 40 0.18 "KL-CV-SO" "683" "G")
  (list "691" "KL-CV_TRANSPORTLEIDING_GVK_300" 40 0.18 "KL-CV-SO" "683" "G")
  (list "692" "KL-CV_TRANSPORTLEIDING_GVK_350" 40 0.18 "KL-CV-SO" "683" "G")
  (list "688" "KL-CV_TRANSPORTLEIDING_GVK_150" 40 0.18 "KL-CV-SO" "683" "G")
  (list "699" "KL-CV_TRANSPORTLEIDING_GVK_800" 40 0.18 "KL-CV-SO" "683" "G")
  (list "1211" "KL-KOUDENET_TRANSPORTLEIDING_RETOUR_GVK" 130 0.18 "KL-KOUDENET-SO" "1210" "G")
  (list "1214" "KL-KOUDENET_TRANSPORTLEIDING_RETOUR_STAAL" 130 0.18 "KL-KOUDENET-SO" "1210" "G")
  (list "1213" "KL-KOUDENET_TRANSPORTLEIDING_RETOUR_PVC" 130 0.18 "KL-KOUDENET-SO" "1210" "G")
  (list "1212" "KL-KOUDENET_TRANSPORTLEIDING_RETOUR_PE" 130 0.18 "KL-KOUDENET-SO" "1210" "G")
  (list "1209" "KL-KOUDENET_TRANSPORTLEIDING_AANVOER_STAAL" 130 0.18 "KL-KOUDENET-SO" "1205" "G")
  (list "1206" "KL-KOUDENET_TRANSPORTLEIDING_AANVOER_GVK" 130 0.18 "KL-KOUDENET-SO" "1205" "G")
  (list "1207" "KL-KOUDENET_TRANSPORTLEIDING_AANVOER_PE" 130 0.18 "KL-KOUDENET-SO" "1205" "G")
  (list "1208" "KL-KOUDENET_TRANSPORTLEIDING_AANVOER_PVC" 130 0.18 "KL-KOUDENET-SO" "1205" "G")
  (list "1192" "KL-KOUDENET_AANSLUITLEIDING_RETOUR_PE" 130 0.18 "KL-KOUDENET-SO" "1190" "G")
  (list "1194" "KL-KOUDENET_AANSLUITLEIDING_RETOUR_STAAL" 130 0.18 "KL-KOUDENET-SO" "1190" "G")
  (list "1191" "KL-KOUDENET_AANSLUITLEIDING_RETOUR_GVK" 130 0.18 "KL-KOUDENET-SO" "1190" "G")
  (list "1193" "KL-KOUDENET_AANSLUITLEIDING_RETOUR_PVC" 130 0.18 "KL-KOUDENET-SO" "1190" "G")
  (list "1187" "KL-KOUDENET_AANSLUITLEIDING_AANVOER_PE" 130 0.18 "KL-KOUDENET-SO" "1185" "G")
  (list "1188" "KL-KOUDENET_AANSLUITLEIDING_AANVOER_PVC" 130 0.18 "KL-KOUDENET-SO" "1185" "G")
  (list "1186" "KL-KOUDENET_AANSLUITLEIDING_AANVOER_GVK" 130 0.18 "KL-KOUDENET-SO" "1185" "G")
  (list "1189" "KL-KOUDENET_AANSLUITLEIDING_AANVOER_STAAL" 130 0.18 "KL-KOUDENET-SO" "1185" "G")
  (list "1300" "KL-WATER_BRANDLEIDING_HUISAANSLUITING_PVC_90" 150 0.18 "KL-WATER-SO" "1293" "G")
  (list "1296" "KL-WATER_BRANDLEIDING_HUISAANSLUITING_PVC_40" 150 0.18 "KL-WATER-SO" "1293" "G")
  (list "1297" "KL-WATER_BRANDLEIDING_HUISAANSLUITING_PVC_50" 150 0.18 "KL-WATER-SO" "1293" "G")
  (list "1294" "KL-WATER_BRANDLEIDING_HUISAANSLUITING_PVC_110" 150 0.18 "KL-WATER-SO" "1293" "G")
  (list "1299" "KL-WATER_BRANDLEIDING_HUISAANSLUITING_PVC_75" 150 0.18 "KL-WATER-SO" "1293" "G")
  (list "1295" "KL-WATER_BRANDLEIDING_HUISAANSLUITING_PVC_32" 150 0.18 "KL-WATER-SO" "1293" "G")
  (list "1298" "KL-WATER_BRANDLEIDING_HUISAANSLUITING_PVC_63" 150 0.18 "KL-WATER-SO" "1293" "G")
  (list "1291" "KL-WATER_BRANDLEIDING_HUISAANSLUITING_PE_75" 150 0.18 "KL-WATER-SO" "1285" "G")
  (list "1292" "KL-WATER_BRANDLEIDING_HUISAANSLUITING_PE_90" 150 0.18 "KL-WATER-SO" "1285" "G")
  (list "1287" "KL-WATER_BRANDLEIDING_HUISAANSLUITING_PE_32" 150 0.18 "KL-WATER-SO" "1285" "G")
  (list "1289" "KL-WATER_BRANDLEIDING_HUISAANSLUITING_PE_50" 150 0.18 "KL-WATER-SO" "1285" "G")
  (list "1286" "KL-WATER_BRANDLEIDING_HUISAANSLUITING_PE_110" 150 0.18 "KL-WATER-SO" "1285" "G")
  (list "1290" "KL-WATER_BRANDLEIDING_HUISAANSLUITING_PE_63" 150 0.18 "KL-WATER-SO" "1285" "G")
  (list "1288" "KL-WATER_BRANDLEIDING_HUISAANSLUITING_PE_40" 150 0.18 "KL-WATER-SO" "1285" "G")
  (list "1319" "KL-WATER_BRANDLEIDING_TRANSPORTLEIDING_PE_400" 150 0.18 "KL-WATER-SO" "1313" "G")
  (list "1315" "KL-WATER_BRANDLEIDING_TRANSPORTLEIDING_PE_125" 150 0.18 "KL-WATER-SO" "1313" "G")
  (list "1318" "KL-WATER_BRANDLEIDING_TRANSPORTLEIDING_PE_315" 150 0.18 "KL-WATER-SO" "1313" "G")
  (list "1320" "KL-WATER_BRANDLEIDING_TRANSPORTLEIDING_PE_500" 150 0.18 "KL-WATER-SO" "1313" "G")
  (list "1316" "KL-WATER_BRANDLEIDING_TRANSPORTLEIDING_PE_160" 150 0.18 "KL-WATER-SO" "1313" "G")
  (list "1314" "KL-WATER_BRANDLEIDING_TRANSPORTLEIDING_PE_110" 150 0.18 "KL-WATER-SO" "1313" "G")
  (list "1321" "KL-WATER_BRANDLEIDING_TRANSPORTLEIDING_PE_630" 150 0.18 "KL-WATER-SO" "1313" "G")
  (list "1317" "KL-WATER_BRANDLEIDING_TRANSPORTLEIDING_PE_250" 150 0.18 "KL-WATER-SO" "1313" "G")
  (list "1329" "KL-WATER_BRANDLEIDING_TRANSPORTLEIDING_PVC_500" 150 0.18 "KL-WATER-SO" "1322" "G")
  (list "1325" "KL-WATER_BRANDLEIDING_TRANSPORTLEIDING_PVC_160" 150 0.18 "KL-WATER-SO" "1322" "G")
  (list "1324" "KL-WATER_BRANDLEIDING_TRANSPORTLEIDING_PVC_125" 150 0.18 "KL-WATER-SO" "1322" "G")
  (list "1323" "KL-WATER_BRANDLEIDING_TRANSPORTLEIDING_PVC_110" 150 0.18 "KL-WATER-SO" "1322" "G")
  (list "1328" "KL-WATER_BRANDLEIDING_TRANSPORTLEIDING_PVC_400" 150 0.18 "KL-WATER-SO" "1322" "G")
  (list "1330" "KL-WATER_BRANDLEIDING_TRANSPORTLEIDING_PVC_630" 150 0.18 "KL-WATER-SO" "1322" "G")
  (list "1327" "KL-WATER_BRANDLEIDING_TRANSPORTLEIDING_PVC_315" 150 0.18 "KL-WATER-SO" "1322" "G")
  (list "1326" "KL-WATER_BRANDLEIDING_TRANSPORTLEIDING_PVC_250" 150 0.18 "KL-WATER-SO" "1322" "G")
  (list "1056" "KL-GAS_HD_HOOFDLEIDING_1 BAR_PE" 30 0.18 "KL-GAS_HD-SO" "1055" "G")
  (list "1063" "KL-GAS_HD_HOOFDLEIDING_1 BAR_PVC" 30 0.18 "KL-GAS_HD-SO" "1055" "G")
  (list "1071" "KL-GAS_HD_HOOFDLEIDING_4 BAR_PE" 30 0.18 "KL-GAS_HD-SO" "1070" "G")
  (list "1078" "KL-GAS_HD_HOOFDLEIDING_4 BAR_PVC" 30 0.18 "KL-GAS_HD-SO" "1070" "G")
  (list "1095" "KL-GAS_HD_HOOFDLEIDING_8 BAR_PVC" 30 0.18 "KL-GAS_HD-SO" "1087" "G")
  (list "1088" "KL-GAS_HD_HOOFDLEIDING_8 BAR_PE" 30 0.18 "KL-GAS_HD-SO" "1087" "G")
  (list "1038" "KL-GAS_HD_AANSLUITLEIDING_8 BAR_PE" 30 0.18 "KL-GAS_HD-SO" "1037" "G")
  (list "1046" "KL-GAS_HD_AANSLUITLEIDING_8 BAR_PVC" 30 0.18 "KL-GAS_HD-SO" "1037" "G")
  (list "1019" "KL-GAS_HD_AANSLUITLEIDING_4 BAR_PE" 30 0.18 "KL-GAS_HD-SO" "1018" "G")
  (list "1027" "KL-GAS_HD_AANSLUITLEIDING_4 BAR_PVC" 30 0.18 "KL-GAS_HD-SO" "1018" "G")
  (list "1002" "KL-GAS_HD_AANSLUITLEIDING_1 BAR_PE" 30 0.18 "KL-GAS_HD-SO" "1001" "G")
  (list "1010" "KL-GAS_HD_AANSLUITLEIDING_1 BAR_PVC" 30 0.18 "KL-GAS_HD-SO" "1001" "G")
  (list "1122" "KL-GAS_LD_AANSLUITLEIDING_100 MBAR_PVC" 50 0.18 "KL-GAS_LD-SO" "1114" "G")
  (list "1115" "KL-GAS_LD_AANSLUITLEIDING_100 MBAR_PE" 50 0.18 "KL-GAS_LD-SO" "1114" "G")
  (list "1130" "KL-GAS_LD_AANSLUITLEIDING_30 MBAR_PE" 50 0.18 "KL-GAS_LD-SO" "1129" "G")
  (list "1137" "KL-GAS_LD_AANSLUITLEIDING_30 MBAR_PVC" 50 0.18 "KL-GAS_LD-SO" "1129" "G")
  (list "1145" "KL-GAS_LD_HOOFDLEIDING_100 MBAR_PE" 50 0.18 "KL-GAS_LD-SO" "1144" "G")
  (list "1152" "KL-GAS_LD_HOOFDLEIDING_100 MBAR_PVC" 50 0.18 "KL-GAS_LD-SO" "1144" "G")
  (list "1160" "KL-GAS_LD_HOOFDLEIDING_30 MBAR_PE" 50 0.18 "KL-GAS_LD-SO" "1159" "G")
  (list "1167" "KL-GAS_LD_HOOFDLEIDING_30 MBAR_PVC" 50 0.18 "KL-GAS_LD-SO" "1159" "G")
  (list "936" "KL-ET_LS_SR_ARMATUUR_PAPLICHT" 190 0.18 "CONTINUOUS" "919" "G")
  (list "927" "KL-ET_LS_SR_ARMATUUR_INVLIEGLICHT" 190 0.18 "CONTINUOUS" "919" "G")
  (list "920" "KL-ET_LS_SR_ARMATUUR_BAANEINDELICHT" 190 0.18 "CONTINUOUS" "919" "G")
  (list "926" "KL-ET_LS_SR_ARMATUUR_HELIPANELLICHT" 190 0.18 "CONTINUOUS" "919" "G")
  (list "937" "KL-ET_LS_SR_ARMATUUR_PLATFORMLICHT" 190 0.18 "CONTINUOUS" "919" "G")
  (list "923" "KL-ET_LS_SR_ARMATUUR_DREMPELLICHT" 190 0.18 "CONTINUOUS" "919" "G")
  (list "941" "KL-ET_LS_SR_ARMATUUR_STARTBAANLICHT" 190 0.18 "CONTINUOUS" "919" "G")
  (list "938" "KL-ET_LS_SR_ARMATUUR_ROLBAANLICHT" 190 0.18 "CONTINUOUS" "919" "G")
  (list "930" "KL-ET_LS_SR_ARMATUUR_NADERINGSLICHT" 190 0.18 "CONTINUOUS" "919" "G")
  (list "933" "KL-ET_LS_SR_ARMATUUR_OVERRUNRANDLICHT" 190 0.18 "CONTINUOUS" "919" "G")
  (list "948" "KL-ET_LS_SR_BORD_INFOBORD" 190 0.18 "CONTINUOUS" "944" "G")
  (list "947" "KL-ET_LS_SR_BORD_HOOKBORD" 190 0.18 "CONTINUOUS" "944" "G")
  (list "946" "KL-ET_LS_SR_BORD_ARRISTOGEARBORD" 190 0.18 "CONTINUOUS" "944" "G")
  (list "945" "KL-ET_LS_SR_BORD_AFSTANDMARKERINGSBORD" 190 0.18 "CONTINUOUS" "944" "G")
  (list "954" "KL-ET_LS_SR_KAST_PUTKAST" 190 0.18 "CONTINUOUS" "953" "G")
  (list "951" "KL-ET_LS_SR_HULPSTUK_MOF" 190 0.18 "CONTINUOUS" "949" "G")
  (list "950" "KL-ET_LS_SR_HULPSTUK_AANSLUITPUNT" 190 0.18 "CONTINUOUS" "949" "G")
  (list "1058" "KL-GAS_HD_HOOFDLEIDING_1 BAR_PE_160" 30 0.18 "KL-GAS_HD-SO" "1056" "G")
  (list "1060" "KL-GAS_HD_HOOFDLEIDING_1 BAR_PE_315" 30 0.18 "KL-GAS_HD-SO" "1056" "G")
  (list "1059" "KL-GAS_HD_HOOFDLEIDING_1 BAR_PE_250" 30 0.18 "KL-GAS_HD-SO" "1056" "G")
  (list "1061" "KL-GAS_HD_HOOFDLEIDING_1 BAR_PE_75" 30 0.18 "KL-GAS_HD-SO" "1056" "G")
  (list "1057" "KL-GAS_HD_HOOFDLEIDING_1 BAR_PE_110" 30 0.18 "KL-GAS_HD-SO" "1056" "G")
  (list "1062" "KL-GAS_HD_HOOFDLEIDING_1 BAR_PE_90" 30 0.18 "KL-GAS_HD-SO" "1056" "G")
  (list "1067" "KL-GAS_HD_HOOFDLEIDING_1 BAR_PVC_315" 30 0.18 "KL-GAS_HD-SO" "1063" "G")
  (list "1069" "KL-GAS_HD_HOOFDLEIDING_1 BAR_PVC_90" 30 0.18 "KL-GAS_HD-SO" "1063" "G")
  (list "1066" "KL-GAS_HD_HOOFDLEIDING_1 BAR_PVC_250" 30 0.18 "KL-GAS_HD-SO" "1063" "G")
  (list "1064" "KL-GAS_HD_HOOFDLEIDING_1 BAR_PVC_110" 30 0.18 "KL-GAS_HD-SO" "1063" "G")
  (list "1068" "KL-GAS_HD_HOOFDLEIDING_1 BAR_PVC_75" 30 0.18 "KL-GAS_HD-SO" "1063" "G")
  (list "1065" "KL-GAS_HD_HOOFDLEIDING_1 BAR_PVC_160" 30 0.18 "KL-GAS_HD-SO" "1063" "G")
  (list "1073" "KL-GAS_HD_HOOFDLEIDING_4 BAR_PE_160" 30 0.18 "KL-GAS_HD-SO" "1071" "G")
  (list "1072" "KL-GAS_HD_HOOFDLEIDING_4 BAR_PE_110" 30 0.18 "KL-GAS_HD-SO" "1071" "G")
  (list "1076" "KL-GAS_HD_HOOFDLEIDING_4 BAR_PE_75" 30 0.18 "KL-GAS_HD-SO" "1071" "G")
  (list "1075" "KL-GAS_HD_HOOFDLEIDING_4 BAR_PE_315" 30 0.18 "KL-GAS_HD-SO" "1071" "G")
  (list "1077" "KL-GAS_HD_HOOFDLEIDING_4 BAR_PE_90" 30 0.18 "KL-GAS_HD-SO" "1071" "G")
  (list "1074" "KL-GAS_HD_HOOFDLEIDING_4 BAR_PE_250" 30 0.18 "KL-GAS_HD-SO" "1071" "G")
  (list "1079" "KL-GAS_HD_HOOFDLEIDING_4 BAR_PVC_110" 30 0.18 "KL-GAS_HD-SO" "1078" "G")
  (list "1084" "KL-GAS_HD_HOOFDLEIDING_4 BAR_PVC_90" 30 0.18 "KL-GAS_HD-SO" "1078" "G")
  (list "1080" "KL-GAS_HD_HOOFDLEIDING_4 BAR_PVC_160" 30 0.18 "KL-GAS_HD-SO" "1078" "G")
  (list "1081" "KL-GAS_HD_HOOFDLEIDING_4 BAR_PVC_250" 30 0.18 "KL-GAS_HD-SO" "1078" "G")
  (list "1083" "KL-GAS_HD_HOOFDLEIDING_4 BAR_PVC_75" 30 0.18 "KL-GAS_HD-SO" "1078" "G")
  (list "1082" "KL-GAS_HD_HOOFDLEIDING_4 BAR_PVC_315" 30 0.18 "KL-GAS_HD-SO" "1078" "G")
  (list "1096" "KL-GAS_HD_HOOFDLEIDING_8 BAR_PVC_110" 30 0.18 "KL-GAS_HD-SO" "1095" "G")
  (list "1097" "KL-GAS_HD_HOOFDLEIDING_8 BAR_PVC_160" 30 0.18 "KL-GAS_HD-SO" "1095" "G")
  (list "1098" "KL-GAS_HD_HOOFDLEIDING_8 BAR_PVC_250" 30 0.18 "KL-GAS_HD-SO" "1095" "G")
  (list "1100" "KL-GAS_HD_HOOFDLEIDING_8 BAR_PVC_75" 30 0.18 "KL-GAS_HD-SO" "1095" "G")
  (list "1101" "KL-GAS_HD_HOOFDLEIDING_8 BAR_PVC_90" 30 0.18 "KL-GAS_HD-SO" "1095" "G")
  (list "1099" "KL-GAS_HD_HOOFDLEIDING_8 BAR_PVC_315" 30 0.18 "KL-GAS_HD-SO" "1095" "G")
  (list "1090" "KL-GAS_HD_HOOFDLEIDING_8 BAR_PE_160" 30 0.18 "KL-GAS_HD-SO" "1088" "G")
  (list "1091" "KL-GAS_HD_HOOFDLEIDING_8 BAR_PE_250" 30 0.18 "KL-GAS_HD-SO" "1088" "G")
  (list "1094" "KL-GAS_HD_HOOFDLEIDING_8 BAR_PE_90" 30 0.18 "KL-GAS_HD-SO" "1088" "G")
  (list "1093" "KL-GAS_HD_HOOFDLEIDING_8 BAR_PE_75" 30 0.18 "KL-GAS_HD-SO" "1088" "G")
  (list "1089" "KL-GAS_HD_HOOFDLEIDING_8 BAR_PE_110" 30 0.18 "KL-GAS_HD-SO" "1088" "G")
  (list "1092" "KL-GAS_HD_HOOFDLEIDING_8 BAR_PE_315" 30 0.18 "KL-GAS_HD-SO" "1088" "G")
  (list "1042" "KL-GAS_HD_AANSLUITLEIDING_8 BAR_PE_50" 30 0.18 "KL-GAS_HD-SO" "1038" "G")
  (list "1045" "KL-GAS_HD_AANSLUITLEIDING_8 BAR_PE_90" 30 0.18 "KL-GAS_HD-SO" "1038" "G")
  (list "1041" "KL-GAS_HD_AANSLUITLEIDING_8 BAR_PE_40" 30 0.18 "KL-GAS_HD-SO" "1038" "G")
  (list "1044" "KL-GAS_HD_AANSLUITLEIDING_8 BAR_PE_75" 30 0.18 "KL-GAS_HD-SO" "1038" "G")
  (list "1043" "KL-GAS_HD_AANSLUITLEIDING_8 BAR_PE_63" 30 0.18 "KL-GAS_HD-SO" "1038" "G")
  (list "1039" "KL-GAS_HD_AANSLUITLEIDING_8 BAR_PE_25" 30 0.18 "KL-GAS_HD-SO" "1038" "G")
  (list "1040" "KL-GAS_HD_AANSLUITLEIDING_8 BAR_PE_32" 30 0.18 "KL-GAS_HD-SO" "1038" "G")
  (list "1048" "KL-GAS_HD_AANSLUITLEIDING_8 BAR_PVC_32" 30 0.18 "KL-GAS_HD-SO" "1046" "G")
  (list "1053" "KL-GAS_HD_AANSLUITLEIDING_8 BAR_PVC_90" 30 0.18 "KL-GAS_HD-SO" "1046" "G")
  (list "1049" "KL-GAS_HD_AANSLUITLEIDING_8 BAR_PVC_40" 30 0.18 "KL-GAS_HD-SO" "1046" "G")
  (list "1050" "KL-GAS_HD_AANSLUITLEIDING_8 BAR_PVC_50" 30 0.18 "KL-GAS_HD-SO" "1046" "G")
  (list "1052" "KL-GAS_HD_AANSLUITLEIDING_8 BAR_PVC_75" 30 0.18 "KL-GAS_HD-SO" "1046" "G")
  (list "1051" "KL-GAS_HD_AANSLUITLEIDING_8 BAR_PVC_63" 30 0.18 "KL-GAS_HD-SO" "1046" "G")
  (list "1047" "KL-GAS_HD_AANSLUITLEIDING_8 BAR_PVC_25" 30 0.18 "KL-GAS_HD-SO" "1046" "G")
  (list "1024" "KL-GAS_HD_AANSLUITLEIDING_4 BAR_PE_63" 30 0.18 "KL-GAS_HD-SO" "1019" "G")
  (list "1022" "KL-GAS_HD_AANSLUITLEIDING_4 BAR_PE_40" 30 0.18 "KL-GAS_HD-SO" "1019" "G")
  (list "1026" "KL-GAS_HD_AANSLUITLEIDING_4 BAR_PE_90" 30 0.18 "KL-GAS_HD-SO" "1019" "G")
  (list "1020" "KL-GAS_HD_AANSLUITLEIDING_4 BAR_PE_25" 30 0.18 "KL-GAS_HD-SO" "1019" "G")
  (list "1021" "KL-GAS_HD_AANSLUITLEIDING_4 BAR_PE_32" 30 0.18 "KL-GAS_HD-SO" "1019" "G")
  (list "1025" "KL-GAS_HD_AANSLUITLEIDING_4 BAR_PE_75" 30 0.18 "KL-GAS_HD-SO" "1019" "G")
  (list "1023" "KL-GAS_HD_AANSLUITLEIDING_4 BAR_PE_50" 30 0.18 "KL-GAS_HD-SO" "1019" "G")
  (list "1032" "KL-GAS_HD_AANSLUITLEIDING_4 BAR_PVC_63" 30 0.18 "KL-GAS_HD-SO" "1027" "G")
  (list "1034" "KL-GAS_HD_AANSLUITLEIDING_4 BAR_PVC_90" 30 0.18 "KL-GAS_HD-SO" "1027" "G")
  (list "1033" "KL-GAS_HD_AANSLUITLEIDING_4 BAR_PVC_75" 30 0.18 "KL-GAS_HD-SO" "1027" "G")
  (list "1028" "KL-GAS_HD_AANSLUITLEIDING_4 BAR_PVC_25" 30 0.18 "KL-GAS_HD-SO" "1027" "G")
  (list "1031" "KL-GAS_HD_AANSLUITLEIDING_4 BAR_PVC_50" 30 0.18 "KL-GAS_HD-SO" "1027" "G")
  (list "1029" "KL-GAS_HD_AANSLUITLEIDING_4 BAR_PVC_32" 30 0.18 "KL-GAS_HD-SO" "1027" "G")
  (list "1030" "KL-GAS_HD_AANSLUITLEIDING_4 BAR_PVC_40" 30 0.18 "KL-GAS_HD-SO" "1027" "G")
  (list "1004" "KL-GAS_HD_AANSLUITLEIDING_1 BAR_PE_32" 30 0.18 "KL-GAS_HD-SO" "1002" "G")
  (list "1009" "KL-GAS_HD_AANSLUITLEIDING_1 BAR_PE_90" 30 0.18 "KL-GAS_HD-SO" "1002" "G")
  (list "1005" "KL-GAS_HD_AANSLUITLEIDING_1 BAR_PE_40" 30 0.18 "KL-GAS_HD-SO" "1002" "G")
  (list "1006" "KL-GAS_HD_AANSLUITLEIDING_1 BAR_PE_50" 30 0.18 "KL-GAS_HD-SO" "1002" "G")
  (list "1008" "KL-GAS_HD_AANSLUITLEIDING_1 BAR_PE_75" 30 0.18 "KL-GAS_HD-SO" "1002" "G")
  (list "1007" "KL-GAS_HD_AANSLUITLEIDING_1 BAR_PE_63" 30 0.18 "KL-GAS_HD-SO" "1002" "G")
  (list "1003" "KL-GAS_HD_AANSLUITLEIDING_1 BAR_PE_25" 30 0.18 "KL-GAS_HD-SO" "1002" "G")
  (list "1017" "KL-GAS_HD_AANSLUITLEIDING_1 BAR_PVC_90" 30 0.18 "KL-GAS_HD-SO" "1010" "G")
  (list "1014" "KL-GAS_HD_AANSLUITLEIDING_1 BAR_PVC_50" 30 0.18 "KL-GAS_HD-SO" "1010" "G")
  (list "1015" "KL-GAS_HD_AANSLUITLEIDING_1 BAR_PVC_63" 30 0.18 "KL-GAS_HD-SO" "1010" "G")
  (list "1016" "KL-GAS_HD_AANSLUITLEIDING_1 BAR_PVC_75" 30 0.18 "KL-GAS_HD-SO" "1010" "G")
  (list "1011" "KL-GAS_HD_AANSLUITLEIDING_1 BAR_PVC_25" 30 0.18 "KL-GAS_HD-SO" "1010" "G")
  (list "1013" "KL-GAS_HD_AANSLUITLEIDING_1 BAR_PVC_40" 30 0.18 "KL-GAS_HD-SO" "1010" "G")
  (list "1012" "KL-GAS_HD_AANSLUITLEIDING_1 BAR_PVC_32" 30 0.18 "KL-GAS_HD-SO" "1010" "G")
  (list "1126" "KL-GAS_LD_AANSLUITLEIDING_100 MBAR_PVC_50" 50 0.18 "KL-GAS_LD-SO" "1122" "G")
  (list "1127" "KL-GAS_LD_AANSLUITLEIDING_100 MBAR_PVC_75" 50 0.18 "KL-GAS_LD-SO" "1122" "G")
  (list "1128" "KL-GAS_LD_AANSLUITLEIDING_100 MBAR_PVC_90" 50 0.18 "KL-GAS_LD-SO" "1122" "G")
  (list "1123" "KL-GAS_LD_AANSLUITLEIDING_100 MBAR_PVC_25" 50 0.18 "KL-GAS_LD-SO" "1122" "G")
  (list "1125" "KL-GAS_LD_AANSLUITLEIDING_100 MBAR_PVC_40" 50 0.18 "KL-GAS_LD-SO" "1122" "G")
  (list "1124" "KL-GAS_LD_AANSLUITLEIDING_100 MBAR_PVC_32" 50 0.18 "KL-GAS_LD-SO" "1122" "G")
  (list "1120" "KL-GAS_LD_AANSLUITLEIDING_100 MBAR_PE_75" 50 0.18 "KL-GAS_LD-SO" "1115" "G")
  (list "1117" "KL-GAS_LD_AANSLUITLEIDING_100 MBAR_PE_32" 50 0.18 "KL-GAS_LD-SO" "1115" "G")
  (list "1118" "KL-GAS_LD_AANSLUITLEIDING_100 MBAR_PE_40" 50 0.18 "KL-GAS_LD-SO" "1115" "G")
  (list "1116" "KL-GAS_LD_AANSLUITLEIDING_100 MBAR_PE_25" 50 0.18 "KL-GAS_LD-SO" "1115" "G")
  (list "1121" "KL-GAS_LD_AANSLUITLEIDING_100 MBAR_PE_90" 50 0.18 "KL-GAS_LD-SO" "1115" "G")
  (list "1119" "KL-GAS_LD_AANSLUITLEIDING_100 MBAR_PE_50" 50 0.18 "KL-GAS_LD-SO" "1115" "G")
  (list "1131" "KL-GAS_LD_AANSLUITLEIDING_30 MBAR_PE_25" 50 0.18 "KL-GAS_LD-SO" "1130" "G")
  (list "1134" "KL-GAS_LD_AANSLUITLEIDING_30 MBAR_PE_50" 50 0.18 "KL-GAS_LD-SO" "1130" "G")
  (list "1132" "KL-GAS_LD_AANSLUITLEIDING_30 MBAR_PE_32" 50 0.18 "KL-GAS_LD-SO" "1130" "G")
  (list "1136" "KL-GAS_LD_AANSLUITLEIDING_30 MBAR_PE_90" 50 0.18 "KL-GAS_LD-SO" "1130" "G")
  (list "1135" "KL-GAS_LD_AANSLUITLEIDING_30 MBAR_PE_75" 50 0.18 "KL-GAS_LD-SO" "1130" "G")
  (list "1133" "KL-GAS_LD_AANSLUITLEIDING_30 MBAR_PE_40" 50 0.18 "KL-GAS_LD-SO" "1130" "G")
  (list "1139" "KL-GAS_LD_AANSLUITLEIDING_30 MBAR_PVC_32" 50 0.18 "KL-GAS_LD-SO" "1137" "G")
  (list "1141" "KL-GAS_LD_AANSLUITLEIDING_30 MBAR_PVC_50" 50 0.18 "KL-GAS_LD-SO" "1137" "G")
  (list "1138" "KL-GAS_LD_AANSLUITLEIDING_30 MBAR_PVC_25" 50 0.18 "KL-GAS_LD-SO" "1137" "G")
  (list "1140" "KL-GAS_LD_AANSLUITLEIDING_30 MBAR_PVC_40" 50 0.18 "KL-GAS_LD-SO" "1137" "G")
  (list "1142" "KL-GAS_LD_AANSLUITLEIDING_30 MBAR_PVC_75" 50 0.18 "KL-GAS_LD-SO" "1137" "G")
  (list "1149" "KL-GAS_LD_HOOFDLEIDING_100 MBAR_PE_315" 50 0.18 "KL-GAS_LD-SO" "1145" "G")
  (list "1146" "KL-GAS_LD_HOOFDLEIDING_100 MBAR_PE_110" 50 0.18 "KL-GAS_LD-SO" "1145" "G")
  (list "1147" "KL-GAS_LD_HOOFDLEIDING_100 MBAR_PE_160" 50 0.18 "KL-GAS_LD-SO" "1145" "G")
  (list "1150" "KL-GAS_LD_HOOFDLEIDING_100 MBAR_PE_75" 50 0.18 "KL-GAS_LD-SO" "1145" "G")
  (list "1148" "KL-GAS_LD_HOOFDLEIDING_100 MBAR_PE_250" 50 0.18 "KL-GAS_LD-SO" "1145" "G")
  (list "1151" "KL-GAS_LD_HOOFDLEIDING_100 MBAR_PE_90" 50 0.18 "KL-GAS_LD-SO" "1145" "G")
  (list "1154" "KL-GAS_LD_HOOFDLEIDING_100 MBAR_PVC_160" 50 0.18 "KL-GAS_LD-SO" "1152" "G")
  (list "1153" "KL-GAS_LD_HOOFDLEIDING_100 MBAR_PVC_110" 50 0.18 "KL-GAS_LD-SO" "1152" "G")
  (list "1155" "KL-GAS_LD_HOOFDLEIDING_100 MBAR_PVC_250" 50 0.18 "KL-GAS_LD-SO" "1152" "G")
  (list "1157" "KL-GAS_LD_HOOFDLEIDING_100 MBAR_PVC_75" 50 0.18 "KL-GAS_LD-SO" "1152" "G")
  (list "1158" "KL-GAS_LD_HOOFDLEIDING_100 MBAR_PVC_90" 50 0.18 "KL-GAS_LD-SO" "1152" "G")
  (list "1156" "KL-GAS_LD_HOOFDLEIDING_100 MBAR_PVC_315" 50 0.18 "KL-GAS_LD-SO" "1152" "G")
  (list "1162" "KL-GAS_LD_HOOFDLEIDING_30 MBAR_PE_160" 50 0.18 "KL-GAS_LD-SO" "1160" "G")
  (list "1161" "KL-GAS_LD_HOOFDLEIDING_30 MBAR_PE_110" 50 0.18 "KL-GAS_LD-SO" "1160" "G")
  (list "1165" "KL-GAS_LD_HOOFDLEIDING_30 MBAR_PE_75" 50 0.18 "KL-GAS_LD-SO" "1160" "G")
  (list "1163" "KL-GAS_LD_HOOFDLEIDING_30 MBAR_PE_250" 50 0.18 "KL-GAS_LD-SO" "1160" "G")
  (list "1164" "KL-GAS_LD_HOOFDLEIDING_30 MBAR_PE_315" 50 0.18 "KL-GAS_LD-SO" "1160" "G")
  (list "1166" "KL-GAS_LD_HOOFDLEIDING_30 MBAR_PE_90" 50 0.18 "KL-GAS_LD-SO" "1160" "G")
  (list "1171" "KL-GAS_LD_HOOFDLEIDING_30 MBAR_PVC_315" 50 0.18 "KL-GAS_LD-SO" "1167" "G")
  (list "1168" "KL-GAS_LD_HOOFDLEIDING_30 MBAR_PVC_110" 50 0.18 "KL-GAS_LD-SO" "1167" "G")
  (list "1169" "KL-GAS_LD_HOOFDLEIDING_30 MBAR_PVC_160" 50 0.18 "KL-GAS_LD-SO" "1167" "G")
  (list "1172" "KL-GAS_LD_HOOFDLEIDING_30 MBAR_PVC_75" 50 0.18 "KL-GAS_LD-SO" "1167" "G")
  (list "1173" "KL-GAS_LD_HOOFDLEIDING_30 MBAR_PVC_90" 50 0.18 "KL-GAS_LD-SO" "1167" "G")
  (list "1170" "KL-GAS_LD_HOOFDLEIDING_30 MBAR_PVC_250" 50 0.18 "KL-GAS_LD-SO" "1167" "G")
  (list "929" "KL-ET_LS_SR_ARMATUUR_INVLIEGLICHT_OPBOUW" 190 0.18 "CONTINUOUS" "927" "G")
  (list "928" "KL-ET_LS_SR_ARMATUUR_INVLIEGLICHT_INBOUW" 190 0.18 "CONTINUOUS" "927" "G")
  (list "921" "KL-ET_LS_SR_ARMATUUR_BAANEINDELICHT_INBOUW" 190 0.18 "CONTINUOUS" "920" "G")
  (list "922" "KL-ET_LS_SR_ARMATUUR_BAANEINDELICHT_OPBOUW" 190 0.18 "CONTINUOUS" "920" "G")
  (list "925" "KL-ET_LS_SR_ARMATUUR_DREMPELLICHT_OPBOUW" 190 0.18 "CONTINUOUS" "923" "G")
  (list "924" "KL-ET_LS_SR_ARMATUUR_DREMPELLICHT_INBOUW" 190 0.18 "CONTINUOUS" "923" "G")
  (list "942" "KL-ET_LS_SR_ARMATUUR_STARTBAANLICHT_INBOUW" 190 0.18 "CONTINUOUS" "941" "G")
  (list "943" "KL-ET_LS_SR_ARMATUUR_STARTBAANLICHT_OPBOUW" 190 0.18 "CONTINUOUS" "941" "G")
  (list "940" "KL-ET_LS_SR_ARMATUUR_ROLBAANLICHT_OPBOUW" 190 0.18 "CONTINUOUS" "938" "G")
  (list "939" "KL-ET_LS_SR_ARMATUUR_ROLBAANLICHT_INBOUW" 190 0.18 "CONTINUOUS" "938" "G")
  (list "932" "KL-ET_LS_SR_ARMATUUR_NADERINGSLICHT_OPBOUW" 190 0.18 "CONTINUOUS" "930" "G")
  (list "931" "KL-ET_LS_SR_ARMATUUR_NADERINGSLICHT_INBOUW" 190 0.18 "CONTINUOUS" "930" "G")
  (list "934" "KL-ET_LS_SR_ARMATUUR_OVERRUNRANDLICHT_INBOUW" 190 0.18 "CONTINUOUS" "933" "G")
  (list "935" "KL-ET_LS_SR_ARMATUUR_OVERRUNRANDLICHT_OPBOUW" 190 0.18 "CONTINUOUS" "933" "G")
  (list "620" "KL-BRANDSTOF" 40 0.18 "KL-BRANDSTOF-SO" "" "")
  (list "1232" "KL-WARMTENET" 80 0.18 "KL-WARMTENET-SO" "" "")
  (list "637" "KL-CHEMIE" 40 0.18 "KL-CHEMIE-SO" "" "")
  (list "1418" "KL-CCTV" 70 0.18 "CONTINUOUS" "" "")
  (list "1264" "KL-WATER" 170 0.18 "KL-WATER-SO" "" "")
  (list "1414" "KL-VEVA" 60 0.18 "CONTINUOUS" "" "")
  (list "1400" "KL-TELPUNT" 100 0.18 "CONTINUOUS" "" "")
  (list "998" "KL-GAS" 30 0.18 "KL-GAS_AL-SO" "" "")
  (list "1388" "KL-DRIP" 170 0.18 "CONTINUOUS" "" "")
  (list "720" "KL-DATA" 90 0.18 "KL-DATA-SO" "" "")
  (list "3118" "KL-COMBIKABEL" 90 0.18 "KL-COMBIKABEL-SO" "" "")
  (list "1385" "KL-WEESLEIDING" 130 0.18 "KL-WEESLEIDING-SO" "" "")
  (list "1416" "KL-AFSLUITINSTALLATIE" 60 0.18 "CONTINUOUS" "" "")
  (list "1410" "KL-UWKS" 130 0.18 "CONTINUOUS" "" "")
  (list "2950" "KL-SCHEMA" 7 0.18 "CONTINUOUS" "" "")
  (list "1386" "KL-BEWEGWIJZERING" 210 0.18 "CONTINUOUS" "" "")
  (list "840" "KL-ET" 10 0.18 "KL-ELECTRICITEIT-SO" "" "")
  (list "1230" "KL-TRACE" 7 0.18 "ZZ-HIDDEN-SO" "" "")
  (list "1222" "KL-OLIE" 40 0.18 "KL-OLIE-SO" "" "")
  (list "645" "KL-CV" 40 0.18 "KL-CV-SO" "" "")
  (list "1396" "KL-WINDWAARSCHUWINGSSYSTEEM" 220 0.18 "CONTINUOUS" "" "")
  (list "1398" "KL-WIM" 150 0.18 "CONTINUOUS" "" "")
  (list "1183" "KL-KOUDENET" 130 0.18 "KL-KOUDENET-SO" "" "")
  (list "1412" "KL-TRANSMISSIE" 80 0.18 "CONTINUOUS" "" "")
  (list "1402" "KL-FILEMELDSYSTEEM" 240 0.18 "CONTINUOUS" "" "")
  (list "1215" "KL-MANTELBUIS" 7 0.18 "CONTINUOUS" "" "")
  (list "1390" "KL-TDI" 200 0.18 "CONTINUOUS" "" "")
  (list "1394" "KL-HOOGTEDETECTIE" 190 0.18 "CONTINUOUS" "" "")
  (list "1406" "KL-VS" 30 0.18 "CONTINUOUS" "" "")
  (list "1221" "KL-STROOK" 7 0.18 "ZZ-HIDDEN-SO" "" "")
  (list "1219" "KL-KATHODISCHE BESCHERMING" 210 0.18 "CONTINUOUS" "" "")
)) *nlcs-layers*))

; Kunstwerken (KW) - 62 lagen
(setq *nlcs-layers* (cons (list "KW" "Kunstwerken" (list
  (list "1454" "KW-KUNSTWERK_TUNNELBAK" 170 0.18 "CONTINUOUS" "1422" "G")
  (list "1439" "KW-KUNSTWERK_REMMINGSWERK" 170 0.18 "CONTINUOUS" "1422" "G")
  (list "1462" "KW-KUNSTWERK_WILDWISSEL" 170 0.18 "CONTINUOUS" "1422" "G")
  (list "1468" "KW-KUNSTWERK_OVERSTORT" 170 0.18 "CONTINUOUS" "1422" "G")
  (list "1469" "KW-KUNSTWERK_SYPHON" 170 0.18 "CONTINUOUS" "1422" "G")
  (list "1431" "KW-KUNSTWERK_GELUIDSWERING" 170 0.18 "CONTINUOUS" "1422" "G")
  (list "1456" "KW-KUNSTWERK_TUNNELBAK_WEGVERKEERSTUNNELBAK" 170 0.18 "CONTINUOUS" "1454" "G")
  (list "1455" "KW-KUNSTWERK_TUNNELBAK_SPOORTUNNELBAK" 170 0.18 "CONTINUOUS" "1454" "G")
  (list "1465" "KW-KUNSTWERK_WILDWISSEL_ECOTUNNEL" 170 0.18 "CONTINUOUS" "1462" "G")
  (list "1443" "KW-KUNSTWERK_SLUIS_KEERSLUIS" 170 0.18 "CONTINUOUS" "1440" "G")
  (list "1445" "KW-KUNSTWERK_SLUIS_TIJSLUIS" 170 0.18 "CONTINUOUS" "1440" "G")
  (list "1442" "KW-KUNSTWERK_SLUIS_INNUNDATIESLUIS" 170 0.18 "CONTINUOUS" "1440" "G")
  (list "1441" "KW-KUNSTWERK_SLUIS_INLAATSLUIS" 170 0.18 "CONTINUOUS" "1440" "G")
  (list "1446" "KW-KUNSTWERK_SLUIS_UITWATERINGSSSLUIS" 170 0.18 "CONTINUOUS" "1440" "G")
  (list "1444" "KW-KUNSTWERK_SLUIS_SCHUTSLUIS" 170 0.18 "CONTINUOUS" "1440" "G")
  (list "1461" "KW-KUNSTWERK_VIADUCT_WEGVERKEERSVIADUCT" 170 0.18 "CONTINUOUS" "1457" "G")
  (list "1460" "KW-KUNSTWERK_VIADUCT_VOETGANGERSVIADUCT" 170 0.18 "CONTINUOUS" "1457" "G")
  (list "1458" "KW-KUNSTWERK_VIADUCT_FIETSVIADUCT" 170 0.18 "CONTINUOUS" "1457" "G")
  (list "1459" "KW-KUNSTWERK_VIADUCT_SPOORVIADUCT" 170 0.18 "CONTINUOUS" "1457" "G")
  (list "1428" "KW-KUNSTWERK_BRUG_WEGVERKEERSBRUG" 170 0.18 "CONTINUOUS" "1424" "G")
  (list "1426" "KW-KUNSTWERK_BRUG_SPOORBRUG" 170 0.18 "CONTINUOUS" "1424" "G")
  (list "1427" "KW-KUNSTWERK_BRUG_VOETGANGERSBRUG" 170 0.18 "CONTINUOUS" "1424" "G")
  (list "1425" "KW-KUNSTWERK_BRUG_FIETSBRUG" 170 0.18 "CONTINUOUS" "1424" "G")
  (list "1453" "KW-KUNSTWERK_TUNNEL_WEGVERKEERTUNNEL" 170 0.18 "CONTINUOUS" "1449" "G")
  (list "1450" "KW-KUNSTWERK_TUNNEL_FIETSTUNNEL" 170 0.18 "CONTINUOUS" "1449" "G")
  (list "1452" "KW-KUNSTWERK_TUNNEL_VOETGANGERSTUNNEL" 170 0.18 "CONTINUOUS" "1449" "G")
  (list "1451" "KW-KUNSTWERK_TUNNEL_SPOORTUNNEL" 170 0.18 "CONTINUOUS" "1449" "G")
  (list "1432" "KW-KUNSTWERK_GELUIDSWERING_SCHERM" 170 0.18 "CONTINUOUS" "1431" "G")
  (list "1467" "KW-KUNSTWERK_WILDWISSEL_ECOTUNNEL_WILDTUNNEL" 170 0.18 "CONTINUOUS" "1465" "G")
  (list "1466" "KW-KUNSTWERK_WILDWISSEL_ECOTUNNEL_VEETUNNEL" 170 0.18 "CONTINUOUS" "1465" "G")
  (list "1464" "KW-KUNSTWERK_WILDWISSEL_ECODUCT_WILDVIADUCT" 170 0.18 "CONTINUOUS" "1463" "G")
  (list "1434" "KW-KUNSTWERK_GELUIDSWERING_SCHERM_BETON" 170 0.18 "CONTINUOUS" "1432" "G")
  (list "1436" "KW-KUNSTWERK_GELUIDSWERING_SCHERM_HOUT" 170 0.18 "CONTINUOUS" "1432" "G")
  (list "1433" "KW-KUNSTWERK_GELUIDSWERING_SCHERM_BEGROEIING" 170 0.18 "CONTINUOUS" "1432" "G")
  (list "1435" "KW-KUNSTWERK_GELUIDSWERING_SCHERM_GLAS" 170 0.18 "CONTINUOUS" "1432" "G")
  (list "1437" "KW-KUNSTWERK_GELUIDSWERING_SCHERM_METAAL" 170 0.18 "CONTINUOUS" "1432" "G")
  (list "1472" "KW-PROFIELVRIJERUIMTE" 7 0.18 "KW-PVR-SO" "" "G")
  (list "1474" "KW-ZICHTRUIMTE" 7 0.18 "KW-ZICHTRUIMTE-SO" "" "G")
  (list "1473" "KW-VOEGOVERGANG" 170 0.18 "CONTINUOUS" "" "G")
  (list "1471" "KW-KUNSTWERK_LANDHOOFD" 170 0.18 "CONTINUOUS" "1422" "G")
  (list "1429" "KW-KUNSTWERK_DUIKER" 170 0.18 "CONTINUOUS" "1422" "G")
  (list "3515" "KW-KUNSTWERK_PERRON" 170 0.18 "CONTINUOUS" "1422" "G")
  (list "1440" "KW-KUNSTWERK_SLUIS" 170 0.18 "CONTINUOUS" "1422" "G")
  (list "1457" "KW-KUNSTWERK_VIADUCT" 170 0.18 "CONTINUOUS" "1422" "G")
  (list "3516" "KW-KUNSTWERK_BODEMVAL" 170 0.18 "CONTINUOUS" "1422" "G")
  (list "1424" "KW-KUNSTWERK_BRUG" 170 0.18 "CONTINUOUS" "1422" "G")
  (list "3512" "KW-KUNSTWERK_SLOOF" 170 0.18 "CONTINUOUS" "1422" "G")
  (list "1430" "KW-KUNSTWERK_FLYOVER" 170 0.18 "CONTINUOUS" "1422" "G")
  (list "3514" "KW-KUNSTWERK_GEMAAL" 170 0.18 "CONTINUOUS" "1422" "G")
  (list "3519" "KW-KUNSTWERK_VOORDE" 170 0.18 "CONTINUOUS" "1422" "G")
  (list "3511" "KW-KUNSTWERK_DEK" 170 0.18 "CONTINUOUS" "1422" "G")
  (list "1449" "KW-KUNSTWERK_TUNNEL" 170 0.18 "CONTINUOUS" "1422" "G")
  (list "3517" "KW-KUNSTWERK_COUPURE" 170 0.18 "CONTINUOUS" "1422" "G")
  (list "1447" "KW-KUNSTWERK_STEIGER" 170 0.18 "CONTINUOUS" "1422" "G")
  (list "1448" "KW-KUNSTWERK_STUW" 170 0.18 "CONTINUOUS" "1422" "G")
  (list "1423" "KW-KUNSTWERK_AQUADUCT" 170 0.18 "CONTINUOUS" "1422" "G")
  (list "3518" "KW-KUNSTWERK_PONTON" 170 0.18 "CONTINUOUS" "1422" "G")
  (list "1470" "KW-KUNSTWERK_PIJLER" 170 0.18 "CONTINUOUS" "1422" "G")
  (list "3513" "KW-KUNSTWERK_PYLOON" 170 0.18 "CONTINUOUS" "1422" "G")
  (list "1438" "KW-KUNSTWERK_OVERKLUIZING" 170 0.18 "CONTINUOUS" "1422" "G")
  (list "1463" "KW-KUNSTWERK_WILDWISSEL_ECODUCT" 170 0.18 "CONTINUOUS" "1462" "G")
  (list "1422" "KW-KUNSTWERK" 170 0.18 "CONTINUOUS" "" "G")
)) *nlcs-layers*))

; Mechanische constructies (MC) - 0 lagen
(setq *nlcs-layers* (cons (list "MC" "Mechanische constructies" (list
)) *nlcs-layers*))

; Milieuonderzoek (MO) - 120 lagen
(setq *nlcs-layers* (cons (list "MO" "Milieuonderzoek" (list
  (list "1486" "MO-ONDERZOEK_SLIBMONSTER" 30 0.18 "CONTINUOUS" "1477" "G/S")
  (list "2912" "MO-ONDERZOEK_STEEK" 30 0.18 "CONTINUOUS" "1477" "G/S")
  (list "1484" "MO-ONDERZOEK_PEILBUIS" 150 0.18 "CONTINUOUS" "1477" "G/S")
  (list "1494" "MO-ONDERZOEK_SPANNINGSMETER" 150 0.18 "CONTINUOUS" "1477" "G/S")
  (list "1480" "MO-ONDERZOEK_BORING" 30 0.18 "CONTINUOUS" "1477" "G/S")
  (list "1478" "MO-ONDERZOEK_SONDERING" 90 0.18 "CONTINUOUS" "1477" "G/S")
  (list "1487" "MO-ONDERZOEK_ZAKBAAK" 190 0.18 "CONTINUOUS" "1477" "G/S")
  (list "2911" "MO-ONDERZOEK_SLEUF" 30 0.18 "CONTINUOUS" "1477" "G/S")
  (list "2913" "MO-ONDERZOEK_VASTPUNT" 30 0.18 "CONTINUOUS" "1477" "G/S")
  (list "1491" "MO-ONDERZOEK_GRAAFGAT" 30 0.18 "CONTINUOUS" "1477" "G/S")
  (list "1490" "MO-ONDERZOEK_MINIFILTER" 30 0.18 "CONTINUOUS" "1477" "G/S")
  (list "1489" "MO-ONDERZOEK_HELLINGMETERBUIS" 30 0.18 "CONTINUOUS" "1477" "G/S")
  (list "3044" "MO-BODEM_NULPUNT" 30 0.18 "CONTINUOUS" "1495" "G/S")
  (list "3042" "MO-BODEM_GEHALTE" 30 0.18 "CONTINUOUS" "1495" "G/S")
  (list "3043" "MO-BODEM_MONSTER" 30 0.18 "CONTINUOUS" "1495" "G/S")
  (list "3041" "MO-BODEM_CONCENTRATIE" 30 0.18 "CONTINUOUS" "1495" "G/S")
  (list "1506" "MO-GRONDWATER" 150 0.18 "CONTINUOUS" "" "G/S")
  (list "1475" "MO-LOCATIE" 30 0.18 "CONTINUOUS" "" "G/S")
  (list "1496" "MO-BODEM_BOORPROFIEL" 30 0.18 "CONTINUOUS" "1495" "G/A")
  (list "1495" "MO-BODEM" 30 0.18 "CONTINUOUS" "" "G/A")
  (list "3132" "MO-GRONDWATER_VERVUILING" 150 0.18 "CONTINUOUS" "1506" "G")
  (list "1509" "MO-GRONDWATER_CONTOUR" 150 0.18 "MO-BORDER-SO" "1506" "G")
  (list "1507" "MO-GRONDWATER_ONDERZOEK" 150 0.18 "CONTINUOUS" "1506" "G")
  (list "1493" "MO-ONDERZOEK_PUIN" 30 0.18 "CONTINUOUS" "1477" "G")
  (list "1578" "MO-SCHADE_METSELWERK" 90 0.18 "CONTINUOUS" "1570" "G")
  (list "1571" "MO-SCHADE_STAAL" 130 0.18 "CONTINUOUS" "1570" "G")
  (list "1576" "MO-SCHADE_FUNDERING" 90 0.18 "CONTINUOUS" "1570" "G")
  (list "1579" "MO-SCHADE_VERHARDING" 130 0.18 "CONTINUOUS" "1570" "G")
  (list "1574" "MO-SCHADE_MECHANISCH" 90 0.18 "CONTINUOUS" "1570" "G")
  (list "1572" "MO-SCHADE_BETON" 252 0.18 "CONTINUOUS" "1570" "G")
  (list "1577" "MO-SCHADE_KUNSTSTOF" 90 0.18 "CONTINUOUS" "1570" "G")
  (list "1573" "MO-SCHADE_HOUT" 40 0.18 "CONTINUOUS" "1570" "G")
  (list "1575" "MO-SCHADE_GRONDKERING" 90 0.18 "CONTINUOUS" "1570" "G")
  (list "1525" "MO-LUCHT_CONTOUR" 7 0.18 "MO-BORDER-SO" "1524" "G")
  (list "1552" "MO-ARCHEOLOGIE_VONDST" 90 0.18 "MO-ARCHEOLOGIE-SO" "1550" "G")
  (list "1551" "MO-ARCHEOLOGIE_VINDPLAATS" 90 0.18 "MO-ARCHEOLOGIE-SO" "1550" "G")
  (list "1557" "MO-ARCHEOLOGIE_NAP" 90 0.18 "MO-ARCHEOLOGIE-SO" "1550" "G")
  (list "1555" "MO-ARCHEOLOGIE_KOLOMOPNAME" 90 0.18 "MO-ARCHEOLOGIE-SO" "1550" "G")
  (list "1553" "MO-ARCHEOLOGIE_SPOOR" 90 0.18 "MO-ARCHEOLOGIE-SO" "1550" "G")
  (list "1556" "MO-ARCHEOLOGIE_GRONDSLAGPUNT" 90 0.18 "MO-ARCHEOLOGIE-SO" "1550" "G")
  (list "1554" "MO-ARCHEOLOGIE_COUPE" 90 0.18 "MO-ARCHEOLOGIE-SO" "1550" "G")
  (list "1558" "MO-ARCHEOLOGIE_MEETLIJN" 90 0.18 "MO-ARCHEOLOGIE-SO" "1550" "G")
  (list "1476" "MO-LOCATIE_FOTO" 30 0.18 "CONTINUOUS" "1475" "G")
  (list "1566" "MO-INSPECTIE_KUNSTSTOF" 90 0.18 "CONTINUOUS" "1559" "G")
  (list "1565" "MO-INSPECTIE_FUNDERING" 90 0.18 "CONTINUOUS" "1559" "G")
  (list "1567" "MO-INSPECTIE_METSELWERK" 90 0.18 "CONTINUOUS" "1559" "G")
  (list "1563" "MO-INSPECTIE_MECHANISCH" 90 0.18 "CONTINUOUS" "1559" "G")
  (list "1568" "MO-INSPECTIE_VERHARDING" 130 0.18 "CONTINUOUS" "1559" "G")
  (list "1560" "MO-INSPECTIE_STAAL" 10 0.18 "CONTINUOUS" "1559" "G")
  (list "1564" "MO-INSPECTIE_GRONDKERING" 90 0.18 "CONTINUOUS" "1559" "G")
  (list "1561" "MO-INSPECTIE_BETON" 90 0.18 "CONTINUOUS" "1559" "G")
  (list "1562" "MO-INSPECTIE_HOUT" 90 0.18 "CONTINUOUS" "1559" "G")
  (list "1545" "MO-GEUR_CONTOUR" 40 0.18 "MO-BORDER-SO" "1544" "G")
  (list "1530" "MO-GELUID_CONTOUR" 10 0.18 "MO-BORDER-SO" "1529" "G")
  (list "1540" "MO-TRILLING_CONTOUR" 210 0.18 "MO-BORDER-SO" "1539" "G")
  (list "1501" "MO-BODEM_VERVUILING" 30 0.18 "MO-BORDER-SO" "1495" "G")
  (list "1497" "MO-BODEM_CONTOUR" 30 0.18 "MO-BORDER-SO" "1495" "G")
  (list "1514" "MO-WATERBODEM_VERVUILING" 30 0.18 "CONTINUOUS" "1513" "G")
  (list "1520" "MO-LICHT_CONTOUR" 130 0.18 "MO-BORDER-SO" "1519" "G")
  (list "1535" "MO-STRALING_CONTOUR" 190 0.18 "MO-BORDER-SO" "1534" "G")
  (list "3134" "MO-GRONDWATER_VERVUILING_GROTER INTERVENTIEWAARDE" 40 0.18 "CONTINUOUS" "3132" "G")
  (list "3133" "MO-GRONDWATER_VERVUILING_GROTER ACHTERGRONDWAARDE" 160 0.18 "CONTINUOUS" "3132" "G")
  (list "3135" "MO-GRONDWATER_VERVUILING_GROTER TUSSENWAARDE" 60 0.18 "CONTINUOUS" "3132" "G")
  (list "3136" "MO-GRONDWATER_VERVUILING_KLEINER ACHTERGRONDWAARDE" 20 0.18 "CONTINUOUS" "3132" "G")
  (list "1512" "MO-GRONDWATER_CONTOUR_INTERVENTIEWAARDE" 10 0.18 "MO-GRONDWATERINTERVENTIEWAARDE-SO" "1509" "G")
  (list "1511" "MO-GRONDWATER_CONTOUR_TUSSENWAARDE" 40 0.18 "MO-GRONDWATERTUSSENWAARDE-SO" "1509" "G")
  (list "1510" "MO-GRONDWATER_CONTOUR_STREEFWAARDE" 90 0.18 "MO-GRONDWATERSTREEFWAARDE-SO" "1509" "G")
  (list "1508" "MO-GRONDWATER_ONDERZOEK_PEILBUIS" 150 0.18 "CONTINUOUS" "1507" "G")
  (list "1580" "MO-SCHADE_VERHARDING_SLIJTLAAG" 170 0.18 "CONTINUOUS" "1579" "G")
  (list "1526" "MO-LUCHT_CONTOUR_STREEFWAARDE" 90 0.18 "MO-LUCHTSTREEFWAARDE-SO" "1525" "G")
  (list "1528" "MO-LUCHT_CONTOUR_INTERVENTIEWAARDE" 10 0.18 "MO-LUCHTINTERVENTIEWAARDE-SO" "1525" "G")
  (list "1527" "MO-LUCHT_CONTOUR_TUSSENWAARDE" 40 0.18 "MO-LUCHTTUSSENWAARDE-SO" "1525" "G")
  (list "3131" "MO-ARCHEOLOGIE_VONDST_WAARDEVOLLE LIJN" 90 0.18 "CONTINUOUS" "1552" "G")
  (list "1569" "MO-INSPECTIE_VERHARDING_SLIJTLAAG" 170 0.18 "CONTINUOUS" "1568" "G")
  (list "1547" "MO-GEUR_CONTOUR_TUSSENWAARDE" 40 0.18 "MO-GEURTUSSENWAARDE-SO" "1545" "G")
  (list "1548" "MO-GEUR_CONTOUR_INTERVENTIEWAARDE" 10 0.18 "MO-GEURINTERVENTIEWAARDE-SO" "1545" "G")
  (list "1546" "MO-GEUR_CONTOUR_STREEFWAARDE" 90 0.18 "MO-GEURSTREEFWAARDE-SO" "1545" "G")
  (list "1533" "MO-GELUID_CONTOUR_INTERVENTIEWAARDE" 10 0.18 "MO-GELUIDINTERVENTIEWAARDE-SO" "1530" "G")
  (list "1532" "MO-GELUID_CONTOUR_TUSSENWAARDE" 40 0.18 "MO-GELUIDTUSSENWAARDE-SO" "1530" "G")
  (list "1531" "MO-GELUID_CONTOUR_STREEFWAARDE" 90 0.18 "MO-GELUIDSTREEFWAARDE-SO" "1530" "G")
  (list "1541" "MO-TRILLING_CONTOUR_STREEFWAARDE" 90 0.18 "MO-TRILLINGSTREEFWAARDE-SO" "1540" "G")
  (list "1543" "MO-TRILLING_CONTOUR_INTERVENTIEWAARDE" 10 0.18 "MO-TRILLINGINTERVENTIEWAARDE-SO" "1540" "G")
  (list "1542" "MO-TRILLING_CONTOUR_TUSSENWAARDE" 40 0.18 "MO-TRILLINGTUSSENWAARDE-SO" "1540" "G")
  (list "1503" "MO-BODEM_VERVUILING_GROTER ACHTERGRONDWAARDE" 130 0.18 "CONTINUOUS" "1501" "G")
  (list "1504" "MO-BODEM_VERVUILING_GROTER TUSSENWAARDE" 50 0.18 "CONTINUOUS" "1501" "G")
  (list "1505" "MO-BODEM_VERVUILING_GROTER INTERVENTIEWAARDE" 10 0.18 "CONTINUOUS" "1501" "G")
  (list "1502" "MO-BODEM_VERVUILING_KLEINER ACHTERGRONDWAARDE" 90 0.18 "CONTINUOUS" "1501" "G")
  (list "1498" "MO-BODEM_CONTOUR_ACHTERGRONDWAARDE" 90 0.18 "MO-BODEMACHTERGRONDWAARDE-SO" "1497" "G")
  (list "1500" "MO-BODEM_CONTOUR_INTERVENTIEWAARDE" 10 0.18 "MO-BODEM_CONTOUR_INTERVENTIEWAARDE-SO" "1497" "G")
  (list "1499" "MO-BODEM_CONTOUR_TUSSENWAARDE" 40 0.18 "MO-BODEMTUSSENWAARDE-SO" "1497" "G")
  (list "1517" "MO-WATERBODEM_VERVUILING_KLASSE B" 190 0.18 "CONTINUOUS" "1514" "G")
  (list "1515" "MO-WATERBODEM_VERVUILING_ACHTERGRONDWAARDE" 90 0.18 "CONTINUOUS" "1514" "G")
  (list "1516" "MO-WATERBODEM_VERVUILING_KLASSE A" 130 0.18 "CONTINUOUS" "1514" "G")
  (list "1518" "MO-WATERBODEM_VERVUILING_NIET TOEPASBAAR" 10 0.18 "CONTINUOUS" "1514" "G")
  (list "1521" "MO-LICHT_CONTOUR_STREEFWAARDE" 90 0.18 "MO-LICHTSTREEFWAARDE-SO" "1520" "G")
  (list "1522" "MO-LICHT_CONTOUR_TUSSENWAARDE" 40 0.18 "MO-LICHTTUSSENWAARDE-SO" "1520" "G")
  (list "1523" "MO-LICHT_CONTOUR_INTERVENTIEWAARDE" 10 0.18 "MO-LICHTINTERVENTIEWAARDE-SO" "1520" "G")
  (list "1538" "MO-STRALING_CONTOUR_INTERVENTIEWAARDE" 10 0.18 "MO-STRALINGINTERVENTIEWAARDE-SO" "1535" "G")
  (list "1537" "MO-STRALING_CONTOUR_TUSSENWAARDE" 40 0.18 "MO-STRALINGTUSSENWAARDE-SO" "1535" "G")
  (list "1536" "MO-STRALING_CONTOUR_STREEFWAARDE" 90 0.18 "MO-STRALINGSTREEFWAARDE-SO" "1535" "G")
  (list "1477" "MO-ONDERZOEK" 30 0.18 "CONTINUOUS" "" "G")
  (list "1570" "MO-SCHADE" 7 0.18 "CONTINUOUS" "" "G")
  (list "1524" "MO-LUCHT" 7 0.18 "CONTINUOUS" "" "G")
  (list "1550" "MO-ARCHEOLOGIE" 90 0.18 "MO-ARCHEOLOGIE-SO" "" "G")
  (list "1559" "MO-INSPECTIE" 7 0.18 "CONTINUOUS" "" "G")
  (list "1544" "MO-GEUR" 40 0.18 "CONTINUOUS" "" "G")
  (list "1529" "MO-GELUID" 10 0.18 "CONTINUOUS" "" "G")
  (list "1539" "MO-TRILLING" 210 0.18 "CONTINUOUS" "" "G")
  (list "3137" "MO-ROUTE GEVAARLIJKE STOFFEN" 20 0.18 "CONTINUOUS" "" "G")
  (list "1549" "MO-EXPLOSIEVEN" 10 0.18 "MO-EXPLOSIEVEN-SO" "" "G")
  (list "1513" "MO-WATERBODEM" 30 0.18 "CONTINUOUS" "" "G")
  (list "1519" "MO-LICHT" 130 0.18 "CONTINUOUS" "" "G")
  (list "1534" "MO-STRALING" 190 0.18 "CONTINUOUS" "" "G")
  (list "3124" "MO-ARCHEOLOGIE_HISTORISCHE KERN" 90 0.18 "MO-ARCHEOLOGIE-SO" "1550" "G")
  (list "3130" "MO-ARCHEOLOGIE_VONDST_WAARDEVOL OBJECT" 90 0.18 "MO-ARCHEOLOGIE-SO" "1552" "G")
  (list "3125" "MO-ARCHEOLOGIE_VINDPLAATS_HOGE VERWACHTING" 90 0.18 "MO-ARCHEOLOGIE-SO" "1551" "G")
  (list "3126" "MO-ARCHEOLOGIE_VINDPLAATS_LAGE VERWACHTING" 90 0.18 "MO-ARCHEOLOGIE-SO" "1551" "G")
  (list "3127" "MO-ARCHEOLOGIE_VINDPLAATS_MIDDELHOGE VERWACHTING" 90 0.18 "MO-ARCHEOLOGIE-SO" "1551" "G")
  (list "3128" "MO-ARCHEOLOGIE_VINDPLAATS_VERSTOORD DOOR ONDERZOEK" 90 0.18 "MO-ARCHEOLOGIE-SO" "1551" "G")
  (list "3129" "MO-ARCHEOLOGIE_VINDPLAATS_VERSTOORD DOOR ONTGRONDING" 90 0.18 "MO-ARCHEOLOGIE-SO" "1551" "G")
)) *nlcs-layers*))

; Metselwerk (MW) - 16 lagen
(setq *nlcs-layers* (cons (list "MW" "Metselwerk" (list
  (list "2858" "MW-AANGRENZENDECONSTRUCTIE_STAAL" 7 0.18 "CONTINUOUS" "2855" "G/A")
  (list "2856" "MW-AANGRENZENDECONSTRUCTIE_BETON" 7 0.18 "CONTINUOUS" "2855" "G/A")
  (list "2857" "MW-AANGRENZENDECONSTRUCTIE_HOUT" 7 0.18 "CONTINUOUS" "2855" "G/A")
  (list "2846" "MW-METSELWERKVORM" 240 0.18 "CONTINUOUS" "" "G/A")
  (list "2855" "MW-AANGRENZENDECONSTRUCTIE" 7 0.18 "CONTINUOUS" "" "G/A")
  (list "2859" "MW-OVERIGMATERIAAL" 7 0.18 "CONTINUOUS" "" "G/A")
  (list "2850" "MW-METSELWERKVORM_CELLENBETON" 240 0.18 "CONTINUOUS" "2846" "G")
  (list "2851" "MW-METSELWERKVORM_NATUURSTEEN" 240 0.18 "CONTINUOUS" "2846" "G")
  (list "2847" "MW-METSELWERKVORM_BAKSTEEN" 240 0.18 "CONTINUOUS" "2846" "G")
  (list "2849" "MW-METSELWERKVORM_KALKZANDSTEEN" 240 0.18 "CONTINUOUS" "2846" "G")
  (list "2848" "MW-METSELWERKVORM_BETONSTEEN" 240 0.18 "CONTINUOUS" "2846" "G")
  (list "2861" "MW-LEVENSDUURVERLENGENDE MAATREGEL" 170 0.18 "CONTINUOUS" "" "G")
  (list "2852" "MW-LATEI" 40 0.18 "CONTINUOUS" "" "G")
  (list "2853" "MW-VERANKERING" 40 0.18 "CONTINUOUS" "" "G")
  (list "2854" "MW-ISOLATIE" 40 0.18 "CONTINUOUS" "" "G")
  (list "2860" "MW-REPARATIES" 170 0.18 "CONTINUOUS" "" "G")
)) *nlcs-layers*))

; Oever- en bodembescherming (OB) - 30 lagen
(setq *nlcs-layers* (cons (list "OB" "Oever- en bodembescherming" (list
  (list "2916" "OB-BEKLEDING_BETON" 253 0.18 "CONTINUOUS" "2914" "G")
  (list "2918" "OB-BEKLEDING_STORTSTEEN" 30 0.18 "CONTINUOUS" "2914" "G")
  (list "2917" "OB-BEKLEDING_BITUMEN" 252 0.18 "CONTINUOUS" "2914" "G")
  (list "2915" "OB-BEKLEDING_STEEN" 30 0.18 "CONTINUOUS" "2914" "G")
  (list "1588" "OB-BESCHOEIING_PERKOENPALENRIJ" 7 0.18 "OB-PERKOEN-SO" "1587" "G")
  (list "1589" "OB-BESCHOEIING_BESCHOEIINGPAAL" 7 0.18 "CONTINUOUS" "1587" "G")
  (list "1592" "OB-DUINBESCHERMING_PERKOENPAAL" 7 0.18 "CONTINUOUS" "1591" "G")
  (list "1605" "OB-OEVERVOORZIENING" 7 0.18 "CONTINUOUS" "" "G")
  (list "1596" "OB-SCHANSKORF" 7 0.18 "OB-SCHANSKORF-SO" "" "G")
  (list "1594" "OB-DIJKBEKLEDING" 7 0.18 "CONTINUOUS" "" "G")
  (list "1597" "OB-NATUUROEVER" 7 0.18 "CONTINUOUS" "" "G")
  (list "2914" "OB-BEKLEDING" 7 0.18 "CONTINUOUS" "" "G")
  (list "1600" "OB-BODEMBESCHERMING" 7 0.18 "CONTINUOUS" "" "G")
  (list "1604" "OB-VERANKERING" 7 0.18 "CONTINUOUS" "" "G")
  (list "1586" "OB-ZETSTEEN" 7 0.18 "CONTINUOUS" "" "G")
  (list "1593" "OB-GOLFBREKER" 7 0.18 "CONTINUOUS" "" "G")
  (list "1581" "OB-PEILVAK" 90 0.18 "OB-PEILVLAK-SO" "" "G")
  (list "1590" "OB-ZINKCONSTRUCTIE" 7 0.18 "CONTINUOUS" "" "G")
  (list "1585" "OB-STORTSTEEN" 7 0.18 "CONTINUOUS" "" "G")
  (list "1587" "OB-BESCHOEIING" 7 0.18 "OB-BESCHOEIING-SO" "" "G")
  (list "1602" "OB-STEENMATRASSEN" 7 0.18 "CONTINUOUS" "" "G")
  (list "1584" "OB-ZAND" 7 0.18 "CONTINUOUS" "" "G")
  (list "1591" "OB-DUINBESCHERMING" 7 0.18 "CONTINUOUS" "" "G")
  (list "1599" "OB-BETUINING" 7 0.18 "CONTINUOUS" "" "G")
  (list "1595" "OB-KRIB" 7 0.18 "CONTINUOUS" "" "G")
  (list "1601" "OB-TALUDBEKLEDING" 7 0.18 "CONTINUOUS" "" "G")
  (list "1598" "OB-NATUURLIJKE BESCHERMING" 7 0.18 "CONTINUOUS" "" "G")
  (list "1583" "OB-KLEI" 7 0.18 "CONTINUOUS" "" "G")
  (list "1603" "OB-STREKDAM" 7 0.18 "CONTINUOUS" "" "G")
  (list "1582" "OB-WATERLIJN" 150 0.18 "CONTINUOUS" "" "G")
)) *nlcs-layers*))

; Ondergrond (OG) - 255 lagen
(setq *nlcs-layers* (cons (list "OG" "Ondergrond" (list
  (list "2489" "OG-WEG_BOUWWEG" 252 0.18 "CONTINUOUS" "1620" "G/S/A")
  (list "3241" "OG-WEG_RIJRICHTING" 7 0.18 "CONTINUOUS" "1620" "G/S")
  (list "3151" "OG-BEBOUWING_ENTREE" 7 0.18 "CONTINUOUS" "1616" "G/S")
  (list "3082" "OG-TOPOGRAFIE_HEK" 7 0.18 "CONTINUOUS" "1615" "G/S")
  (list "3152" "OG-BEBOUWING_ENTREE_GARAGE" 7 0.18 "CONTINUOUS" "3151" "G/S")
  (list "1625" "OG-HOOGTEPUNT" 7 0.18 "CONTINUOUS" "" "G/S")
  (list "3153" "OG-BEBOUWING_FIETSENSTALLING" 7 0.18 "CONTINUOUS" "1616" "G/S")
  (list "3163" "OG-BEBOUWING_LAGE TRAFO" 7 0.18 "CONTINUOUS" "1616" "G/S")
  (list "3168" "OG-BEBOUWING_OPENBAAR TOILET" 7 0.18 "CONTINUOUS" "1616" "G/S")
  (list "3529" "OG-WATER_SLIK" 170 0.18 "CONTINUOUS" "1619" "G/S")
  (list "3444" "OG-TERREIN_GEVEL" 7 0.18 "CONTINUOUS" "3264" "G/S")
  (list "3277" "OG-TERREIN_HONDENUITLAATPLAATS" 7 0.18 "CONTINUOUS" "3264" "G/S")
  (list "3258" "OG-ZONE_LEIDINGSTROOK" 7 0.18 "CONTINUOUS" "3254" "G/A")
  (list "3260" "OG-ZONE_BELEMMERING" 7 0.18 "CONTINUOUS" "3254" "G/A")
  (list "3257" "OG-ZONE_HOOGSPANNINGSTRACE" 7 0.18 "CONTINUOUS" "3254" "G/A")
  (list "3259" "OG-ZONE_LPG" 7 0.18 "CONTINUOUS" "3254" "G/A")
  (list "3261" "OG-ZONE_BELEMMERING_LEIDINGSTROOK" 7 0.18 "CONTINUOUS" "3260" "G/A")
  (list "3262" "OG-ZONE_BELEMMERING_OBJECT" 7 0.18 "CONTINUOUS" "3260" "G/A")
  (list "3171" "OG-BEBOUWING_OVERBOUWING_MET KOPPELBALKEN" 7 0.18 "CONTINUOUS" "3170" "G/A")
  (list "1619" "OG-WATER" 130 0.18 "CONTINUOUS" "" "G/S")
  (list "3446" "OG-WATER_SLOOT" 120 0.18 "CONTINUOUS" "1619" "G/S")
  (list "3290" "OG-TERREIN_ONBEGROEID" 7 0.18 "CONTINUOUS" "3264" "G/S")
  (list "3442" "OG-TERREIN_ERF" 7 0.18 "CONTINUOUS" "3264" "G/S")
  (list "3291" "OG-TERREIN_ONBEGROEID_STRAND" 7 0.18 "CONTINUOUS" "3290" "G/S")
  (list "3443" "OG-TERREIN_ONBEGROEID_ZANDVERSTUIVING" 7 0.18 "CONTINUOUS" "3290" "G/S")
  (list "3263" "OG-ZONE_BESCHERMD STADS EN DORPSGEZICHT" 7 0.18 "RO-BESCHERMDSTADSGEZICHT-SO" "3254" "G/A")
  (list "3255" "OG-ZONE_ECOGEBIED" 7 0.18 "CONTINUOUS" "3254" "G/A")
  (list "3256" "OG-ZONE_GEVAARLIJKE STOFFEN" 7 0.18 "CONTINUOUS" "3254" "G/A")
  (list "3146" "OG-BEBOUWING_BORDES" 7 0.18 "CONTINUOUS" "1616" "G/A")
  (list "3170" "OG-BEBOUWING_OVERBOUWING" 7 0.18 "CONTINUOUS" "1616" "G/A")
  (list "3164" "OG-BEBOUWING_LUIFEL" 7 0.18 "CONTINUOUS" "1616" "G/A")
  (list "3225" "OG-WEG_BUSBAAN" 7 0.18 "CONTINUOUS" "1620" "G")
  (list "3227" "OG-WEG_FIETSENSTALLING" 7 0.18 "CONTINUOUS" "1620" "G")
  (list "3237" "OG-WEG_PARKEERSECTIE" 7 0.18 "CONTINUOUS" "1620" "G")
  (list "3229" "OG-WEG_ONVERHARD" 7 0.18 "CONTINUOUS" "1620" "G")
  (list "3228" "OG-WEG_HOOFDSTRUCTUUR" 7 0.18 "CONTINUOUS" "1620" "G")
  (list "3240" "OG-WEG_RIJCURVE" 7 0.18 "ZZ-HIDDEN-SO" "1620" "G")
  (list "3230" "OG-WEG_PARKEERPLAATS" 7 0.18 "CONTINUOUS" "1620" "G")
  (list "3148" "OG-BEBOUWING_CULTUUR EN ONTSPANNING" 7 0.18 "CONTINUOUS" "1616" "G")
  (list "3158" "OG-BEBOUWING_HOOGTESCHEIDING" 7 0.18 "CONTINUOUS" "1616" "G")
  (list "1617" "OG-BEBOUWING_HUISNUMMER" 7 0.18 "CONTINUOUS" "1616" "G")
  (list "3182" "OG-BEBOUWING_WONINGBOUW" 7 0.18 "CONTINUOUS" "1616" "G")
  (list "3159" "OG-BEBOUWING_HORECA" 7 0.18 "CONTINUOUS" "1616" "G")
  (list "3165" "OG-BEBOUWING_MAATSCHAPPELIJK" 7 0.18 "CONTINUOUS" "1616" "G")
  (list "3174" "OG-BEBOUWING_PIJLER VIADUCT" 7 0.18 "CONTINUOUS" "1616" "G")
  (list "3166" "OG-BEBOUWING_MOLEN" 7 0.18 "CONTINUOUS" "1616" "G")
  (list "3147" "OG-BEBOUWING_CENTRUM" 7 0.18 "CONTINUOUS" "1616" "G")
  (list "3150" "OG-BEBOUWING_DIENSTVERLENING" 7 0.18 "CONTINUOUS" "1616" "G")
  (list "3162" "OG-BEBOUWING_KOLOM GEBOUW" 7 0.18 "CONTINUOUS" "1616" "G")
  (list "3149" "OG-BEBOUWING_DETAILHANDEL" 7 0.18 "CONTINUOUS" "1616" "G")
  (list "3178" "OG-BEBOUWING_TUSSENMUUR" 7 0.18 "CONTINUOUS" "1616" "G")
  (list "3154" "OG-BEBOUWING_FUNDERING" 7 0.18 "ZZ-HIDDEN-SO" "1616" "G")
  (list "3139" "OG-BEBOUWING_BEDRIJVEN" 7 0.18 "CONTINUOUS" "1616" "G")
  (list "1618" "OG-BEBOUWING_STRAATNAAM" 7 0.18 "CONTINUOUS" "1616" "G")
  (list "3155" "OG-BEBOUWING_GEMENGD" 7 0.18 "CONTINUOUS" "1616" "G")
  (list "3160" "OG-BEBOUWING_KANTOOR" 7 0.18 "CONTINUOUS" "1616" "G")
  (list "3219" "OG-WATER_POEL" 7 0.18 "CONTINUOUS" "1619" "G")
  (list "3221" "OG-WATER_VIJVER" 7 0.18 "CONTINUOUS" "1619" "G")
  (list "1629" "OG-HOOGTELIJN_MAJOR" 7 0.18 "CONTINUOUS" "1627" "G")
  (list "1628" "OG-HOOGTELIJN_MINOR" 253 0.18 "CONTINUOUS" "1627" "G")
  (list "3278" "OG-TERREIN_KOPPELING" 7 0.18 "CONTINUOUS" "3264" "G")
  (list "3315" "OG-TERREIN_UITGEEFBAAR" 7 0.18 "CONTINUOUS" "3264" "G")
  (list "3287" "OG-TERREIN_NATUUR" 7 0.18 "CONTINUOUS" "3264" "G")
  (list "3288" "OG-TERREIN_NIET UITGEEFBAAR" 7 0.18 "CONTINUOUS" "3264" "G")
  (list "3267" "OG-TERREIN_BEDRIJVENTERREIN" 7 0.18 "CONTINUOUS" "3264" "G")
  (list "3301" "OG-TERREIN_SPORT" 7 0.18 "CONTINUOUS" "3264" "G")
  (list "1623" "OG-TERREIN_CULTUURSCHEIDING" 7 0.18 "CONTINUOUS" "3264" "G")
  (list "3331" "OG-TERREIN_WOONGEBIED" 7 0.18 "CONTINUOUS" "3264" "G")
  (list "3300" "OG-TERREIN_RECREATIE" 7 0.18 "CONTINUOUS" "3264" "G")
  (list "3265" "OG-TERREIN_AGRARISCH" 7 0.18 "CONTINUOUS" "3264" "G")
  (list "3328" "OG-TERREIN_UIT TE WERKEN" 7 0.18 "CONTINUOUS" "3264" "G")
  (list "1614" "OG-GRONDGEBRUIK_NIET INGERICHT" 40 0.18 "CONTINUOUS" "1612" "G")
  (list "1613" "OG-GRONDGEBRUIK_INGERICHT" 40 0.18 "CONTINUOUS" "1612" "G")
  (list "3226" "OG-WEG_BUSBAAN_DYNAMISCH" 7 0.18 "CONTINUOUS" "3225" "G")
  (list "3232" "OG-WEG_PARKEERPLAATS_INDELING" 7 0.18 "CONTINUOUS" "3230" "G")
  (list "3233" "OG-WEG_PARKEERPLAATS_INVALIDE" 7 0.18 "CONTINUOUS" "3230" "G")
  (list "3234" "OG-WEG_PARKEERPLAATS_LAAD EN LOS" 7 0.18 "CONTINUOUS" "3230" "G")
  (list "3236" "OG-WEG_PARKEERPLAATS_VERGUNNINGHOUDER" 7 0.18 "CONTINUOUS" "3230" "G")
  (list "3231" "OG-WEG_PARKEERPLAATS_BETAALD" 7 0.18 "CONTINUOUS" "3230" "G")
  (list "3235" "OG-WEG_PARKEERPLAATS_PRIVE" 7 0.18 "CONTINUOUS" "3230" "G")
  (list "3183" "OG-BEBOUWING_WONINGBOUW_WONINGSCHEIDING" 7 0.18 "CONTINUOUS" "3182" "G")
  (list "3216" "OG-WATER_HAVEN_HAVENVAK" 7 0.18 "CONTINUOUS" "3215" "G")
  (list "3282" "OG-TERREIN_KOPPELING_INDUSTRIELAWAAI" 7 0.18 "CONTINUOUS" "3278" "G")
  (list "3284" "OG-TERREIN_KOPPELING_VERKEERSLAWAAI" 7 0.18 "CONTINUOUS" "3278" "G")
  (list "3283" "OG-TERREIN_KOPPELING_AGRARISCH GEBIED" 7 0.18 "CONTINUOUS" "3278" "G")
  (list "3280" "OG-TERREIN_KOPPELING_BRUG" 7 0.18 "CONTINUOUS" "3278" "G")
  (list "3279" "OG-TERREIN_KOPPELING_UITWERKINGSPLAN" 7 0.18 "CONTINUOUS" "3278" "G")
  (list "3281" "OG-TERREIN_KOPPELING_BOUWVERGUNNING" 7 0.18 "CONTINUOUS" "3278" "G")
  (list "3326" "OG-TERREIN_UITGEEFBAAR_DETAILHANDEL" 7 0.18 "CONTINUOUS" "3315" "G")
  (list "3319" "OG-TERREIN_UITGEEFBAAR_KOOP" 7 0.18 "CONTINUOUS" "3315" "G")
  (list "3317" "OG-TERREIN_UITGEEFBAAR_HUUR" 7 0.18 "CONTINUOUS" "3315" "G")
  (list "3322" "OG-TERREIN_UITGEEFBAAR_VRIJE SECTOR" 7 0.18 "CONTINUOUS" "3315" "G")
  (list "3316" "OG-TERREIN_UITGEEFBAAR_KAVEL" 7 0.18 "CONTINUOUS" "3315" "G")
  (list "3327" "OG-TERREIN_UITGEEFBAAR_HORECA" 7 0.18 "CONTINUOUS" "3315" "G")
  (list "3324" "OG-TERREIN_UITGEEFBAAR_MAATSCHAPPELIJKE VOORZIENING" 7 0.18 "CONTINUOUS" "3315" "G")
  (list "3325" "OG-TERREIN_UITGEEFBAAR_KANTOOR" 7 0.18 "CONTINUOUS" "3315" "G")
  (list "3289" "OG-TERREIN_NIET UITGEEFBAAR_KAVEL" 7 0.18 "CONTINUOUS" "3288" "G")
  (list "3272" "OG-TERREIN_BEGROEID_BOS" 7 0.18 "CONTINUOUS" "3271" "G")
  (list "3273" "OG-TERREIN_BEGROEID_TUIN" 7 0.18 "CONTINUOUS" "3271" "G")
  (list "3266" "OG-TERREIN_AGRARISCH_MET WAARDEN" 7 0.18 "CONTINUOUS" "3265" "G")
  (list "3185" "OG-BEBOUWING_WONINGBOUW_HUUR_SOCIAAL" 7 0.18 "CONTINUOUS" "3184" "G")
  (list "3186" "OG-BEBOUWING_WONINGBOUW_HUUR_VRIJE SECTOR" 7 0.18 "CONTINUOUS" "3184" "G")
  (list "3189" "OG-BEBOUWING_WONINGBOUW_KOOP_SOCIAAL" 7 0.18 "CONTINUOUS" "3187" "G")
  (list "3188" "OG-BEBOUWING_WONINGBOUW_KOOP_PARTICULIER OPDRACHTGEVERSCHAP" 7 0.18 "CONTINUOUS" "3187" "G")
  (list "3285" "OG-TERREIN_KOPPELING_VERKEERSLAWAAI_AUTOSNELWEG" 7 0.18 "CONTINUOUS" "3284" "G")
  (list "3321" "OG-TERREIN_UITGEEFBAAR_KOOP_PARTICULIER OPDRACHTGEVERSCHAP" 7 0.18 "CONTINUOUS" "3319" "G")
  (list "3320" "OG-TERREIN_UITGEEFBAAR_KOOP_SOCIAAL" 7 0.18 "CONTINUOUS" "3319" "G")
  (list "3318" "OG-TERREIN_UITGEEFBAAR_HUUR_SOCIAAL" 7 0.18 "CONTINUOUS" "3317" "G")
  (list "3323" "OG-TERREIN_UITGEEFBAAR_VRIJE SECTOR_PARTICULIER OPDRACHTGEVERSCHAP" 7 0.18 "CONTINUOUS" "3322" "G")
  (list "3337" "OG-FASE4" 7 0.18 "CONTINUOUS" "" "G")
  (list "3254" "OG-ZONE" 7 0.18 "ZZ-HIDDEN-SO" "" "G")
  (list "1608" "OG-DWM" 7 0.18 "CONTINUOUS" "" "G")
  (list "3334" "OG-FASE1" 7 0.18 "CONTINUOUS" "" "G")
  (list "1627" "OG-HOOGTELIJN" 7 0.18 "CONTINUOUS" "" "G")
  (list "1624" "OG-INFO" 7 0.18 "CONTINUOUS" "" "G")
  (list "1606" "OG-DTB" 7 0.18 "CONTINUOUS" "" "G")
  (list "3024" "OG-KADASTRAAL" 7 0.18 "CONTINUOUS" "" "G")
  (list "1609" "OG-GBKN" 7 0.18 "CONTINUOUS" "" "G")
  (list "3340" "OG-FASE7" 7 0.18 "CONTINUOUS" "" "G")
  (list "1632" "OG-VLAKVERDICHTINGSLIJN" 253 0.18 "CONTINUOUS" "" "G")
  (list "1612" "OG-GRONDGEBRUIK" 40 0.18 "CONTINUOUS" "" "G")
  (list "3335" "OG-FASE2" 7 0.18 "CONTINUOUS" "" "G")
  (list "1610" "OG-TOPOKAART" 7 0.18 "CONTINUOUS" "" "G")
  (list "2919" "OG-HULPLIJN" 50 0.18 "CONTINUOUS" "" "G")
  (list "3336" "OG-FASE3" 7 0.18 "CONTINUOUS" "" "G")
  (list "3339" "OG-FASE6" 7 0.18 "CONTINUOUS" "" "G")
  (list "3338" "OG-FASE5" 7 0.18 "CONTINUOUS" "" "G")
  (list "1631" "OG-GRID" 253 0.18 "CONTINUOUS" "" "G")
  (list "1626" "OG-COORDINAAT" 7 0.18 "CONTINUOUS" "" "G")
  (list "1621" "OG-SPOORBAAN" 7 0.18 "CONTINUOUS" "" "G")
  (list "1607" "OG-DTM" 7 0.18 "CONTINUOUS" "" "G")
  (list "1633" "OG-BREUKLIJN" 7 0.18 "CONTINUOUS" "" "G")
  (list "1611" "OG-BEHEERKAART" 7 0.18 "CONTINUOUS" "" "G")
  (list "1615" "OG-TOPOGRAFIE" 7 0.18 "CONTINUOUS" "" "G")
  (list "3023" "OG-GRENS" 7 0.18 "CONTINUOUS" "" "G/S")
  (list "1630" "OG-TRIANGULATIE" 253 0.18 "CONTINUOUS" "" "G")
  (list "3248" "OG-WEG_VERHARD" 7 0.18 "CONTINUOUS" "1620" "G")
  (list "3252" "OG-WEG_WEGVAK" 7 0.18 "CONTINUOUS" "1620" "G")
  (list "3246" "OG-WEG_TRAMBAAN" 7 0.18 "CONTINUOUS" "1620" "G")
  (list "3239" "OG-WEG_PLEIN" 7 0.18 "CONTINUOUS" "1620" "G")
  (list "3245" "OG-WEG_SPOORBAAN" 7 0.18 "CONTINUOUS" "1620" "G")
  (list "3242" "OG-WEG_RIJWEG" 7 0.18 "CONTINUOUS" "1620" "G")
  (list "3238" "OG-WEG_PARKEERZONE" 7 0.18 "CONTINUOUS" "1620" "G")
  (list "3249" "OG-WEG_VOETPAD" 7 0.18 "CONTINUOUS" "1620" "G")
  (list "3244" "OG-WEG_RIJWIELPAD" 7 0.18 "CONTINUOUS" "1620" "G")
  (list "4036" "OG-BEBOUWING_ZONNEPANEEL" 150 0.18 "CONTINUOUS" "1616" "G")
  (list "3145" "OG-BEBOUWING_BIJZONDERE DOELEINDEN" 7 0.18 "CONTINUOUS" "1616" "G")
  (list "3143" "OG-BEBOUWING_BIJGEBOUW" 7 0.18 "CONTINUOUS" "1616" "G")
  (list "3172" "OG-BEBOUWING_OVERIG" 7 0.18 "CONTINUOUS" "1616" "G")
  (list "4037" "OG-BEBOUWING_POMP" 150 0.18 "CONTINUOUS" "1616" "G")
  (list "3173" "OG-BEBOUWING_PARKEERGARAGE" 7 0.18 "CONTINUOUS" "1616" "G")
  (list "3176" "OG-BEBOUWING_TRAFOHUISJE" 7 0.18 "CONTINUOUS" "1616" "G")
  (list "3177" "OG-BEBOUWING_TRAP" 7 0.18 "CONTINUOUS" "1616" "G")
  (list "3212" "OG-BEBOUWING_WOONWAGENS" 7 0.18 "CONTINUOUS" "1616" "G")
  (list "3167" "OG-BEBOUWING_NUTSGEBOUW" 7 0.18 "CONTINUOUS" "1616" "G")
  (list "3138" "OG-BEBOUWING_TE AMOVEREN" 7 0.18 "CONTINUOUS" "1616" "G")
  (list "3179" "OG-BEBOUWING_UITBOUW" 7 0.18 "CONTINUOUS" "1616" "G")
  (list "3169" "OG-BEBOUWING_OPTIE" 7 0.18 "CONTINUOUS" "1616" "G")
  (list "3161" "OG-BEBOUWING_KIOSK" 7 0.18 "CONTINUOUS" "1616" "G")
  (list "3181" "OG-BEBOUWING_WINDTURBINE" 7 0.18 "CONTINUOUS" "1616" "G")
  (list "3157" "OG-BEBOUWING_HOOFDGEBOUW" 7 0.18 "CONTINUOUS" "1616" "G")
  (list "3175" "OG-BEBOUWING_TE HANDHAVEN" 7 0.18 "CONTINUOUS" "1616" "G")
  (list "3156" "OG-BEBOUWING_GEZONDHEIDSZORG" 7 0.18 "CONTINUOUS" "1616" "G")
  (list "3213" "OG-WATER_BEEK" 150 0.18 "CONTINUOUS" "1619" "G")
  (list "3521" "OG-WATER_ZEE" 170 0.18 "CONTINUOUS" "1619" "G")
  (list "3214" "OG-WATER_GRACHT" 160 0.18 "CONTINUOUS" "1619" "G")
  (list "3223" "OG-WATER_WOONBOOTLOCATIE" 7 0.18 "CONTINUOUS" "1619" "G")
  (list "3218" "OG-WATER_MEER" 140 0.18 "CONTINUOUS" "1619" "G")
  (list "3220" "OG-WATER_RIVIER" 130 0.18 "CONTINUOUS" "1619" "G")
  (list "3215" "OG-WATER_HAVEN" 170 0.18 "CONTINUOUS" "1619" "G")
  (list "3222" "OG-WATER_WATERSPORT" 7 0.18 "CONTINUOUS" "1619" "G")
  (list "3217" "OG-WATER_KANAAL" 120 0.18 "CONTINUOUS" "1619" "G")
  (list "3302" "OG-TERREIN_TRANSACTIE" 7 0.18 "CONTINUOUS" "3264" "G")
  (list "3297" "OG-TERREIN_PLANGEBIED" 7 0.18 "CONTINUOUS" "3264" "G")
  (list "3268" "OG-TERREIN_BEGRAAFPLAATS" 7 0.18 "CONTINUOUS" "3264" "G")
  (list "3271" "OG-TERREIN_BEGROEID" 7 0.18 "CONTINUOUS" "3264" "G")
  (list "3295" "OG-TERREIN_PARK" 7 0.18 "CONTINUOUS" "3264" "G")
  (list "3329" "OG-TERREIN_VERHARD" 7 0.18 "CONTINUOUS" "3264" "G")
  (list "3332" "OG-TERREIN_WOONWAGENLOCATIE" 7 0.18 "CONTINUOUS" "3264" "G")
  (list "3293" "OG-TERREIN_ONVERHARD" 7 0.18 "CONTINUOUS" "3264" "G")
  (list "3294" "OG-TERREIN_OPENBAAR GEBIED" 7 0.18 "CONTINUOUS" "3264" "G")
  (list "3253" "OG-WEG_WEGVAK_WEGVAKONDERDEEL" 7 0.18 "CONTINUOUS" "3252" "G")
  (list "3243" "OG-WEG_RIJWEG_RIJWEGVAK" 7 0.18 "CONTINUOUS" "3242" "G")
  (list "3251" "OG-WEG_VOETPAD_VOETPADVAK" 7 0.18 "CONTINUOUS" "3249" "G")
  (list "3250" "OG-WEG_VOETPAD_TRAP" 7 0.18 "CONTINUOUS" "3249" "G")
  (list "3184" "OG-BEBOUWING_WONINGBOUW_HUUR" 7 0.18 "CONTINUOUS" "3182" "G")
  (list "3211" "OG-BEBOUWING_WONINGBOUW_STARTERSWONING" 7 0.18 "CONTINUOUS" "3182" "G")
  (list "3199" "OG-BEBOUWING_WONINGBOUW_VRIJSTAAND" 7 0.18 "CONTINUOUS" "3182" "G")
  (list "3191" "OG-BEBOUWING_WONINGBOUW_HOOGBOUW" 7 0.18 "CONTINUOUS" "3182" "G")
  (list "3203" "OG-BEBOUWING_WONINGBOUW_TWEE ONDER EEN KAP" 7 0.18 "CONTINUOUS" "3182" "G")
  (list "3187" "OG-BEBOUWING_WONINGBOUW_KOOP" 7 0.18 "CONTINUOUS" "3182" "G")
  (list "3207" "OG-BEBOUWING_WONINGBOUW_EENGEZINSWONING" 7 0.18 "CONTINUOUS" "3182" "G")
  (list "3195" "OG-BEBOUWING_WONINGBOUW_LAAGBOUW" 7 0.18 "CONTINUOUS" "3182" "G")
  (list "3190" "OG-BEBOUWING_WONINGBOUW_GESTAPELD" 7 0.18 "CONTINUOUS" "3182" "G")
  (list "3144" "OG-BEBOUWING_BIJGEBOUW_OPTIE" 7 0.18 "CONTINUOUS" "3143" "G")
  (list "3180" "OG-BEBOUWING_UITBOUW_ZWEVEND" 7 0.18 "CONTINUOUS" "3179" "G")
  (list "3142" "OG-BEBOUWING_BEDRIJVEN_DETAILHANDEL" 7 0.18 "CONTINUOUS" "3139" "G")
  (list "3141" "OG-BEBOUWING_BEDRIJVEN_GROOTBEDRIJF" 7 0.18 "CONTINUOUS" "3139" "G")
  (list "3140" "OG-BEBOUWING_BEDRIJVEN_MKB" 7 0.18 "CONTINUOUS" "3139" "G")
  (list "3224" "OG-WATER_WOONBOOTLOCATIE_LIGPLAATS" 7 0.18 "CONTINUOUS" "3223" "G")
  (list "3307" "OG-TERREIN_TRANSACTIE_VERHUUR" 7 0.18 "CONTINUOUS" "3302" "G")
  (list "3313" "OG-TERREIN_TRANSACTIE_VERPACHTING" 7 0.18 "CONTINUOUS" "3302" "G")
  (list "3311" "OG-TERREIN_TRANSACTIE_OPSTAL" 7 0.18 "CONTINUOUS" "3302" "G")
  (list "3314" "OG-TERREIN_TRANSACTIE_VOORKEURSRECHT" 7 0.18 "CONTINUOUS" "3302" "G")
  (list "3305" "OG-TERREIN_TRANSACTIE_VERKOOP" 7 0.18 "CONTINUOUS" "3302" "G")
  (list "3310" "OG-TERREIN_TRANSACTIE_ONTEIGENING" 7 0.18 "CONTINUOUS" "3302" "G")
  (list "3308" "OG-TERREIN_TRANSACTIE_RUILING" 7 0.18 "CONTINUOUS" "3302" "G")
  (list "3304" "OG-TERREIN_TRANSACTIE_AANKOOP" 7 0.18 "CONTINUOUS" "3302" "G")
  (list "3309" "OG-TERREIN_TRANSACTIE_INGEBRUIKGAVE" 7 0.18 "CONTINUOUS" "3302" "G")
  (list "3306" "OG-TERREIN_TRANSACTIE_ERFPACHT" 7 0.18 "CONTINUOUS" "3302" "G")
  (list "3312" "OG-TERREIN_TRANSACTIE_OVERDRACHT" 7 0.18 "CONTINUOUS" "3302" "G")
  (list "3303" "OG-TERREIN_TRANSACTIE_VERKOOPGEGEVENS" 7 0.18 "CONTINUOUS" "3302" "G")
  (list "3298" "OG-TERREIN_PLANGEBIED_BRUTO" 7 0.18 "CONTINUOUS" "3297" "G")
  (list "3299" "OG-TERREIN_PLANGEBIED_NETTO" 7 0.18 "CONTINUOUS" "3297" "G")
  (list "3269" "OG-TERREIN_BEGRAAFPLAATS_GRAFVAK" 7 0.18 "CONTINUOUS" "3268" "G")
  (list "3296" "OG-TERREIN_PARK_STADSPARK" 7 0.18 "CONTINUOUS" "3295" "G")
  (list "3330" "OG-TERREIN_VERHARD_TERRAS" 7 0.18 "CONTINUOUS" "3329" "G")
  (list "3333" "OG-TERREIN_WOONWAGENLOCATIE_STANDPLAATS" 7 0.18 "CONTINUOUS" "3332" "G")
  (list "3201" "OG-BEBOUWING_WONINGBOUW_VRIJSTAAND_MIDDELDUUR" 7 0.18 "CONTINUOUS" "3199" "G")
  (list "3200" "OG-BEBOUWING_WONINGBOUW_VRIJSTAAND_DUUR" 7 0.18 "CONTINUOUS" "3199" "G")
  (list "3202" "OG-BEBOUWING_WONINGBOUW_VRIJSTAAND_GOEDKOOP" 7 0.18 "CONTINUOUS" "3199" "G")
  (list "3194" "OG-BEBOUWING_WONINGBOUW_HOOGBOUW_GOEDKOOP" 7 0.18 "CONTINUOUS" "3191" "G")
  (list "3192" "OG-BEBOUWING_WONINGBOUW_HOOGBOUW_DUUR" 7 0.18 "CONTINUOUS" "3191" "G")
  (list "3193" "OG-BEBOUWING_WONINGBOUW_HOOGBOUW_MIDDELDUUR" 7 0.18 "CONTINUOUS" "3191" "G")
  (list "3204" "OG-BEBOUWING_WONINGBOUW_TWEE ONDER EEN KAP_DUUR" 7 0.18 "CONTINUOUS" "3203" "G")
  (list "3205" "OG-BEBOUWING_WONINGBOUW_TWEE ONDER EEN KAP_MIDDELDUUR" 7 0.18 "CONTINUOUS" "3203" "G")
  (list "3206" "OG-BEBOUWING_WONINGBOUW_TWEE ONDER EEN KAP_GOEDKOOP" 7 0.18 "CONTINUOUS" "3203" "G")
  (list "3210" "OG-BEBOUWING_WONINGBOUW_EENGEZINSWONING_GOEDKOOP" 7 0.18 "CONTINUOUS" "3207" "G")
  (list "3208" "OG-BEBOUWING_WONINGBOUW_EENGEZINSWONING_DUUR" 7 0.18 "CONTINUOUS" "3207" "G")
  (list "3209" "OG-BEBOUWING_WONINGBOUW_EENGEZINSWONING_MIDDELDUUR" 7 0.18 "CONTINUOUS" "3207" "G")
  (list "3197" "OG-BEBOUWING_WONINGBOUW_LAAGBOUW_MIDDELDUUR" 7 0.18 "CONTINUOUS" "3195" "G")
  (list "3198" "OG-BEBOUWING_WONINGBOUW_LAAGBOUW_GOEDKOOP" 7 0.18 "CONTINUOUS" "3195" "G")
  (list "3196" "OG-BEBOUWING_WONINGBOUW_LAAGBOUW_DUUR" 7 0.18 "CONTINUOUS" "3195" "G")
  (list "3270" "OG-TERREIN_BEGRAAFPLAATS_GRAFVAK_GRAF" 7 0.18 "CONTINUOUS" "3269" "G")
  (list "3292" "OG-TERREIN_ONBEGROEID_STRAND_STRANDVAK" 7 0.18 "CONTINUOUS" "3291" "G")
  (list "3274" "OG-TERREIN_BEGROEID_TUIN_ECOTUIN" 7 0.18 "CONTINUOUS" "3273" "G")
  (list "3276" "OG-TERREIN_BEGROEID_TUIN_VOLKSTUIN" 7 0.18 "CONTINUOUS" "3273" "G")
  (list "3275" "OG-TERREIN_BEGROEID_TUIN_TUINBOUW" 7 0.18 "CONTINUOUS" "3273" "G")
  (list "1620" "OG-WEG" 7 0.18 "CONTINUOUS" "" "G")
  (list "1616" "OG-BEBOUWING" 7 0.35 "CONTINUOUS" "" "G")
  (list "3264" "OG-TERREIN" 7 0.18 "CONTINUOUS" "" "G")
  (list "3450" "OG-GREPPEL" 30 0.18 "CONTINUOUS" "" "G")
  (list "3522" "OG-BEBOUWING_LOODS" 7 0.18 "CONTINUOUS" "1616" "G")
  (list "3528" "OG-BEBOUWING_SCHUUR" 7 0.18 "CONTINUOUS" "1616" "G")
  (list "3525" "OG-BEBOUWING_BASSIN" 7 0.18 "CONTINUOUS" "1616" "G")
  (list "3523" "OG-BEBOUWING_OPSLAGTANK" 7 0.18 "CONTINUOUS" "1616" "G")
  (list "3527" "OG-BEBOUWING_SILO" 7 0.18 "CONTINUOUS" "1616" "G")
  (list "3524" "OG-BEBOUWING_BEZINKTANK" 7 0.18 "CONTINUOUS" "1616" "G")
  (list "3526" "OG-BEBOUWING_BUNKER" 7 0.18 "CONTINUOUS" "1616" "G")
  (list "3447" "OG-WATER_BRON" 130 0.18 "CONTINUOUS" "1619" "G")
  (list "3449" "OG-WATER_GREPPEL" 160 0.18 "CONTINUOUS" "1619" "G")
  (list "3530" "OG-TERREIN_OEVER" 7 0.18 "CONTINUOUS" "3264" "G")
  (list "3520" "OG-TERREIN_ONBEGROEID_ZAND" 7 0.18 "CONTINUOUS" "3290" "G")
  (list "3247" "OG-WEG_TAXISTANDPLAATS" 7 0.18 "CONTINUOUS" "1620" "G/S")
  (list "3286" "OG-TERREIN_MILIEUBESCHERMINGSGEBIED" 7 0.18 "CONTINUOUS" "3264" "G/A")
)) *nlcs-layers*))

; Openbare verlichting (OV) - 44 lagen
(setq *nlcs-layers* (cons (list "OV" "Openbare verlichting" (list
  (list "3545" "OV-KAST_ONTSTEEKPUNT" 190 0.18 "CONTINUOUS" "907" "G/S")
  (list "3544" "OV-KAST_HOOGSPANNING" 190 0.18 "CONTINUOUS" "907" "G/S")
  (list "910" "OV-KAST_PUTKAST" 190 0.18 "CONTINUOUS" "907" "G/S")
  (list "3547" "OV-KAST_TRANSFORMATORKAST" 190 0.18 "CONTINUOUS" "907" "G/S")
  (list "3546" "OV-KAST_SEKTIEKAST" 190 0.18 "CONTINUOUS" "907" "G/S")
  (list "3543" "OV-KAST_DOORVERBINDINGSKAST" 190 0.18 "CONTINUOUS" "907" "G/S")
  (list "3548" "OV-KAST_VOEDINGSPUNT" 190 0.18 "CONTINUOUS" "907" "G/S")
  (list "888" "OV-ARMATUUR_BOLDER" 190 0.18 "CONTINUOUS" "887" "G/S")
  (list "892" "OV-ARMATUUR_SCHIJNWERPER" 190 0.18 "CONTINUOUS" "887" "G/S")
  (list "3533" "OV-ARMATUUR_SPOT" 190 0.18 "CONTINUOUS" "887" "G/S")
  (list "895" "OV-HULPSTUK_MOF" 190 0.18 "CONTINUOUS" "893" "G/S")
  (list "3534" "OV-HULPSTUK_LAS" 190 0.18 "CONTINUOUS" "893" "G/S")
  (list "894" "OV-HULPSTUK_AANSLUITPUNT" 190 0.18 "CONTINUOUS" "893" "G/S")
  (list "3532" "OV-AARDING_AARDELECTRODE" 7 0.18 "CONTINUOUS" "3531" "G/S")
  (list "907" "OV-KAST" 190 0.18 "CONTINUOUS" "" "G/S")
  (list "911" "OV-LICHTMAST" 190 0.18 "CONTINUOUS" "" "G/S")
  (list "887" "OV-ARMATUUR" 7 0.18 "CONTINUOUS" "" "G/S")
  (list "906" "OV-KABELROL" 190 0.18 "CONTINUOUS" "" "G/S")
  (list "893" "OV-HULPSTUK" 190 0.18 "CONTINUOUS" "" "G/S")
  (list "890" "OV-GRONDSPOT" 190 0.18 "CONTINUOUS" "" "G/S")
  (list "3531" "OV-AARDING" 7 0.18 "OV-AARDING-SO" "" "G/S")
  (list "904" "OV-KABELDOORVOER_KABELKOKER" 7 0.18 "OV-KABELKOKER-SO" "902" "G")
  (list "905" "OV-KABELDOORVOER_MANTELBUIS" 7 0.18 "CONTINUOUS" "902" "G")
  (list "903" "OV-KABELDOORVOER_KABELGOOT" 7 0.18 "CONTINUOUS" "902" "G")
  (list "908" "OV-KAST_LASKAST" 190 0.18 "CONTINUOUS" "907" "G")
  (list "909" "OV-KAST_OVKAST" 190 0.18 "CONTINUOUS" "907" "G")
  (list "3539" "OV-TRACE_WENSTRACE" 7 0.18 "ZZ-HIDDEN-SO" "3538" "G")
  (list "889" "OV-ARMATUUR_FUNCTIONEEL" 190 0.18 "CONTINUOUS" "887" "G")
  (list "891" "OV-ARMATUUR_ORIENTATIE" 190 0.18 "CONTINUOUS" "887" "G")
  (list "901" "OV-KABEL_VOEDINGSKABEL" 190 0.18 "OV-KABEL_VOEDING-SO" "897" "G")
  (list "3536" "OV-KABEL_COMBIKABEL" 190 0.18 "OV-COMBIKABEL-SO" "897" "G")
  (list "899" "OV-KABEL_BUNDEL" 190 0.18 "OV-KABEL_BUNDEL-SO" "897" "G")
  (list "3535" "OV-KABEL_AANSLUITKABEL" 190 0.18 "OV-KABEL-SO" "897" "G")
  (list "898" "OV-KABEL_AARDING" 190 0.18 "OV-KABEL_AARDING-SO" "897" "G")
  (list "900" "OV-KABEL_SIGNAALKABEL" 190 0.18 "OV-KABEL_SIGNAAL-SO" "897" "G")
  (list "902" "OV-KABELDOORVOER" 7 0.18 "CONTINUOUS" "" "G")
  (list "3538" "OV-TRACE" 7 0.18 "ZZ-HIDDEN-SO" "" "G")
  (list "897" "OV-KABEL" 190 0.18 "OV-KABEL-SO" "" "G")
  (list "3542" "OV-LIJNVERLICHTING" 190 0.18 "OV-LIJNV-SO" "" "G")
  (list "3537" "OV-STROOK" 7 0.18 "ZZ-HIDDEN-SO" "" "G")
  (list "915" "OV-PUT" 7 0.18 "CONTINUOUS" "" "G")
  (list "3541" "OV-DRAAGCONSTRUCTIE" 190 0.18 "CONTINUOUS" "" "G")
  (list "3540" "OV-WEESLEIDING" 190 0.18 "OV-WEESLEIDING-SO" "" "G")
  (list "913" "OV-MANTELBUIS" 7 0.18 "CONTINUOUS" "" "G")
)) *nlcs-layers*))

; Riolering (RI) - 1078 lagen
(setq *nlcs-layers* (cons (list "RI" "Riolering" (list
  (list "4074" "RI-OVERIG_UITLAATCONSTRUCTIE" 10 0.18 "CONTINUOUS" "2052" "G/S")
  (list "2082" "RI-OVERIG_STROMINGSRICHTING" 10 0.18 "CONTINUOUS" "2052" "G/S")
  (list "4072" "RI-OVERIG_LOZEPUT" 10 0.18 "CONTINUOUS" "2052" "G/S")
  (list "3046" "RI-OVERIG_TANK" 10 0.18 "CONTINUOUS" "2052" "G/S")
  (list "2080" "RI-OVERIG_PUTNUMMER" 10 0.18 "CONTINUOUS" "2052" "G/S")
  (list "3049" "RI-OVERIG_TERREINKAST" 10 0.18 "CONTINUOUS" "2052" "G/S")
  (list "2079" "RI-OVERIG_PUTDEKSELNIVEAU" 10 0.18 "CONTINUOUS" "2052" "G/S")
  (list "1832" "RI-HWA_RIOOLPUT" 150 0.18 "CONTINUOUS" "1786" "G/S")
  (list "3800" "RI-HWA_AANSLUITPUT" 150 0.18 "CONTINUOUS" "1786" "G/S")
  (list "3486" "RI-HWA_SCHILDMUUR" 150 0.18 "CONTINUOUS" "1786" "G/S")
  (list "1809" "RI-HWA_HULPSTUK" 150 0.18 "CONTINUOUS" "1786" "G/S")
  (list "1812" "RI-HWA_KOLK" 150 0.18 "CONTINUOUS" "1786" "G/S")
  (list "1830" "RI-HWA_PUTDEKSELNIVEAU" 150 0.18 "CONTINUOUS" "1786" "G/S")
  (list "4049" "RI-HWA_LOZEPUT" 150 0.18 "CONTINUOUS" "1786" "G/S")
  (list "1942" "RI-HWA_UITLAATCONSTRUCTIE" 150 0.18 "CONTINUOUS" "1786" "G/S")
  (list "1859" "RI-HWA_STROMINGSRICHTING" 150 0.18 "CONTINUOUS" "1786" "G/S")
  (list "1831" "RI-HWA_PUTNUMMER" 150 0.18 "CONTINUOUS" "1786" "G/S")
  (list "1787" "RI-HWA_BOB" 150 0.18 "CONTINUOUS" "1786" "G/S")
  (list "1958" "RI-ITR_HULPSTUK" 50 0.18 "CONTINUOUS" "1944" "G/S")
  (list "2050" "RI-ITR_UITLAATCONSTRUCTIE" 50 0.18 "CONTINUOUS" "1944" "G/S")
  (list "1989" "RI-ITR_RIOOLPUT" 50 0.18 "CONTINUOUS" "1944" "G/S")
  (list "1945" "RI-ITR_BOB" 50 0.18 "CONTINUOUS" "1944" "G/S")
  (list "1977" "RI-ITR_PUTDEKSELNIVEAU" 50 0.18 "CONTINUOUS" "1944" "G/S")
  (list "1961" "RI-ITR_KOLK" 50 0.18 "CONTINUOUS" "1944" "G/S")
  (list "3844" "RI-ITR_SCHILDMUUR" 50 0.18 "CONTINUOUS" "1944" "G/S")
  (list "3836" "RI-ITR_AANSLUITPUT" 50 0.18 "CONTINUOUS" "1944" "G/S")
  (list "4053" "RI-ITR_DOORSPOELPUT" 50 0.18 "CONTINUOUS" "1944" "G/S")
  (list "4054" "RI-ITR_LOZEPUT" 50 0.18 "CONTINUOUS" "1944" "G/S")
  (list "1978" "RI-ITR_PUTNUMMER" 50 0.18 "CONTINUOUS" "1944" "G/S")
  (list "2016" "RI-ITR_STROMINGSRICHTING" 50 0.18 "CONTINUOUS" "1944" "G/S")
  (list "2241" "RI-DWA_HULPSTUK" 20 0.18 "CONTINUOUS" "2220" "G/S")
  (list "2221" "RI-DWA_AFSCHEIDER" 20 0.18 "CONTINUOUS" "2220" "G/S")
  (list "2284" "RI-DWA_SEPTICTANK" 20 0.18 "CONTINUOUS" "2220" "G/S")
  (list "4044" "RI-DWA_UITLAATCONSTRUCTIE" 20 0.18 "CONTINUOUS" "2220" "G/S")
  (list "2250" "RI-DWA_RIOOLPUT" 20 0.18 "CONTINUOUS" "2220" "G/S")
  (list "4014" "RI-DWA_LOZEPUT" 20 0.18 "CONTINUOUS" "2220" "G/S")
  (list "2225" "RI-DWA_BOB" 20 0.18 "CONTINUOUS" "2220" "G/S")
  (list "2248" "RI-DWA_PUTDEKSELNIVEAU" 20 0.18 "CONTINUOUS" "2220" "G/S")
  (list "4017" "RI-DWA_SCHILDMUUR" 20 0.18 "CONTINUOUS" "2220" "G/S")
  (list "2285" "RI-DWA_STROMINGSRICHTING" 20 0.18 "CONTINUOUS" "2220" "G/S")
  (list "2249" "RI-DWA_PUTNUMMER" 20 0.18 "CONTINUOUS" "2220" "G/S")
  (list "3998" "RI-DWA_AANSLUITPUT" 20 0.18 "CONTINUOUS" "2220" "G/S")
  (list "2208" "RI-VACUUMLEIDING_HULPSTUK" 10 0.18 "CONTINUOUS" "2194" "G/S")
  (list "2214" "RI-VACUUMLEIDING_RIOOLPUT" 10 0.18 "CONTINUOUS" "2194" "G/S")
  (list "2206" "RI-VACUUMLEIDING_GEMAAL" 10 0.18 "CONTINUOUS" "2194" "G/S")
  (list "2212" "RI-VACUUMLEIDING_PUTDEKSELNIVEAU" 10 0.18 "CONTINUOUS" "2194" "G/S")
  (list "2218" "RI-VACUUMLEIDING_STROMINGSRICHTING" 10 0.18 "CONTINUOUS" "2194" "G/S")
  (list "2204" "RI-VACUUMLEIDING_BOB" 10 0.18 "CONTINUOUS" "2194" "G/S")
  (list "2213" "RI-VACUUMLEIDING_PUTNUMMER" 10 0.18 "CONTINUOUS" "2194" "G/S")
  (list "2066" "RI-PERSLEIDING_GEMAAL" 210 0.18 "CONTINUOUS" "2054" "G/S")
  (list "2074" "RI-PERSLEIDING_RIOOLPUT" 210 0.18 "CONTINUOUS" "2054" "G/S")
  (list "4081" "RI-PERSLEIDING_LOZEPUT" 210 0.18 "CONTINUOUS" "2054" "G/S")
  (list "2078" "RI-PERSLEIDING_STROMINGSRICHTING" 210 0.18 "RI-PERS-SO" "2054" "G/S")
  (list "2068" "RI-PERSLEIDING_HULPSTUK" 210 0.18 "CONTINUOUS" "2054" "G/S")
  (list "2064" "RI-PERSLEIDING_BOB" 210 0.18 "CONTINUOUS" "2054" "G/S")
  (list "2072" "RI-PERSLEIDING_PUTDEKSELNIVEAU" 210 0.18 "CONTINUOUS" "2054" "G/S")
  (list "2073" "RI-PERSLEIDING_PUTNUMMER" 210 0.18 "CONTINUOUS" "2054" "G/S")
  (list "4083" "RI-PERSLEIDING_UITLAATCONSTRUCTIE" 210 0.18 "CONTINUOUS" "2054" "G/S")
  (list "1685" "RI-GWA_KOLK" 30 0.18 "CONTINUOUS" "1664" "G/S")
  (list "1703" "RI-GWA_RIOOLPUT" 30 0.18 "CONTINUOUS" "1664" "G/S")
  (list "3675" "RI-GWA_AANSLUITPUT" 30 0.18 "CONTINUOUS" "1664" "G/S")
  (list "1681" "RI-GWA_HULPSTUK" 30 0.18 "CONTINUOUS" "1664" "G/S")
  (list "4048" "RI-GWA_UITLAATCONSTRUCTIE" 30 0.18 "CONTINUOUS" "1664" "G/S")
  (list "1665" "RI-GWA_BOB" 30 0.18 "CONTINUOUS" "1664" "G/S")
  (list "3686" "RI-GWA_LOZEPUT" 30 0.18 "CONTINUOUS" "1664" "G/S")
  (list "1730" "RI-GWA_STROMINGSRICHTING" 30 0.18 "CONTINUOUS" "1664" "G/S")
  (list "1701" "RI-GWA_PUTDEKSELNIVEAU" 30 0.18 "CONTINUOUS" "1664" "G/S")
  (list "1702" "RI-GWA_PUTNUMMER" 30 0.18 "CONTINUOUS" "1664" "G/S")
  (list "3485" "RI-GWA_SCHILDMUUR" 30 0.18 "CONTINUOUS" "1664" "G/S")
  (list "1656" "RI-DRAINAGE_PUT" 90 0.18 "CONTINUOUS" "1635" "G/S")
  (list "1637" "RI-DRAINAGE_BOB" 90 0.18 "CONTINUOUS" "1635" "G/S")
  (list "1653" "RI-DRAINAGE_HULPSTUK" 90 0.18 "CONTINUOUS" "1635" "G/S")
  (list "1660" "RI-DRAINAGE_PUTNUMMER" 90 0.18 "CONTINUOUS" "1635" "G/S")
  (list "1659" "RI-DRAINAGE_PUTDEKSELNIVEAU" 90 0.18 "CONTINUOUS" "1635" "G/S")
  (list "3500" "RI-DRAINAGE_UITLAATCONSTRUCTIE" 90 0.18 "CONTINUOUS" "1635" "G/S")
  (list "3599" "RI-DRAINAGE_SCHILDMUUR" 90 0.18 "CONTINUOUS" "1635" "G/S")
  (list "4038" "RI-DRAINAGE_LOZEPUT" 90 0.18 "CONTINUOUS" "1635" "G/S")
  (list "1662" "RI-DRAINAGE_TALUDGOOT" 90 0.18 "CONTINUOUS" "1635" "G/S")
  (list "3065" "RI-OVERIG_RIOOLPUT_BETON" 10 0.18 "CONTINUOUS" "3064" "G/S")
  (list "3865" "RI-OVERIG_RIOOLPUT-VOLSCHUIMEN" 10 0.18 "CONTINUOUS" "3064" "G/S")
  (list "3066" "RI-OVERIG_RIOOLPUT_KUNSTSTOF" 10 0.18 "CONTINUOUS" "3064" "G/S")
  (list "3067" "RI-OVERIG_RIOOLPUT_METSELWERK" 10 0.18 "CONTINUOUS" "3064" "G/S")
  (list "3482" "RI-OVERIG_RIOOLPUT_INSPECTIE" 10 0.18 "CONTINUOUS" "3064" "G/S")
  (list "3866" "RI-OVERIG_RIOOLPUT-VOLZANDEN" 10 0.18 "CONTINUOUS" "3064" "G/S")
  (list "3483" "RI-OVERIG_RIOOLPUT-OPHOOGTEBRENGEN" 10 0.18 "RI-OPHOOGTEBRENGEN-SO" "3064" "G/S")
  (list "3864" "RI-OVERIG_RIOOLPUT-LINING" 10 0.18 "RI-LINING-SO" "3064" "G/S")
  (list "3796" "RI-HWA_RIOOLPUT-LINING" 150 0.18 "RI-LINING-SO" "1832" "G/S")
  (list "1851" "RI-HWA_RIOOLPUT_STUWPUT" 150 0.18 "CONTINUOUS" "1832" "G/S")
  (list "4052" "RI-HWA_RIOOLPUT_ZANDVANGPUT" 150 0.18 "CONTINUOUS" "1832" "G/S")
  (list "3798" "RI-HWA_RIOOLPUT-VOLZANDEN" 150 0.18 "CONTINUOUS" "1832" "G/S")
  (list "1834" "RI-HWA_RIOOLPUT_BLINDEPUT" 150 0.18 "CONTINUOUS" "1832" "G/S")
  (list "3795" "RI-HWA_RIOOLPUT-OPHOOGTEBRENGEN" 150 0.18 "RI-OPHOOGTEBRENGEN-SO" "1832" "G/S")
  (list "1845" "RI-HWA_RIOOLPUT_OVERSTORTPUT" 150 0.18 "CONTINUOUS" "1832" "G/S")
  (list "3793" "RI-HWA_RIOOLPUT_KUNSTSTOF" 150 0.18 "CONTINUOUS" "1832" "G/S")
  (list "1848" "RI-HWA_RIOOLPUT_POMPPUT" 150 0.18 "CONTINUOUS" "1832" "G/S")
  (list "1839" "RI-HWA_RIOOLPUT_INSPECTIEPUT" 150 0.18 "CONTINUOUS" "1832" "G/S")
  (list "3797" "RI-HWA_RIOOLPUT-VOLSCHUIMEN" 150 0.18 "CONTINUOUS" "1832" "G/S")
  (list "1854" "RI-HWA_RIOOLPUT_VALPUT" 150 0.18 "CONTINUOUS" "1832" "G/S")
  (list "3792" "RI-HWA_RIOOLPUT_BETON" 150 0.18 "CONTINUOUS" "1832" "G/S")
  (list "3794" "RI-HWA_RIOOLPUT_METSELWERK" 150 0.18 "CONTINUOUS" "1832" "G/S")
  (list "1858" "RI-HWA_RIOOLPUT_KRUISINGSPUT" 150 0.18 "CONTINUOUS" "1832" "G/S")
  (list "1842" "RI-HWA_AANSLUITPUT_ONTSTOPPINGSPUT" 150 0.18 "CONTINUOUS" "3800" "G/S")
  (list "3697" "RI-HWA_HULPSTUK_AFSLUITER" 150 0.18 "CONTINUOUS" "1809" "G/S")
  (list "3704" "RI-HWA_HULPSTUK_VERLOOPSTUK" 150 0.18 "CONTINUOUS" "1809" "G/S")
  (list "3703" "RI-HWA_HULPSTUK_SPUIKRAAN" 150 0.18 "CONTINUOUS" "1809" "G/S")
  (list "3702" "RI-HWA_HULPSTUK_SCHOONMAAKSTUK" 150 0.18 "CONTINUOUS" "1809" "G/S")
  (list "3700" "RI-HWA_HULPSTUK_KEERKLEP" 150 0.18 "CONTINUOUS" "1809" "G/S")
  (list "3705" "RI-HWA_HULPSTUK_VLINDERKLEP" 150 0.18 "CONTINUOUS" "1809" "G/S")
  (list "3701" "RI-HWA_HULPSTUK_ONTLUCHTING" 150 0.18 "CONTINUOUS" "1809" "G/S")
  (list "3698" "RI-HWA_HULPSTUK_BELUCHTING" 150 0.18 "CONTINUOUS" "1809" "G/S")
  (list "3699" "RI-HWA_HULPSTUK_EINDKAP" 150 0.18 "CONTINUOUS" "1809" "G/S")
  (list "1814" "RI-HWA_KOLK_RWSKOLK" 150 0.18 "CONTINUOUS" "1812" "G/S")
  (list "1813" "RI-HWA_KOLK_COMBIKOLK" 150 0.18 "CONTINUOUS" "1812" "G/S")
  (list "1815" "RI-HWA_KOLK_STRAATKOLK" 150 0.18 "CONTINUOUS" "1812" "G/S")
  (list "3707" "RI-HWA_KOLK-OPHOOGTEBRENGEN" 150 0.18 "RI-OPHOOGTEBRENGEN-SO" "1812" "G/S")
  (list "1816" "RI-HWA_KOLK_TROTTOIRKOLK" 150 0.18 "CONTINUOUS" "1812" "G/S")
  (list "3706" "RI-HWA_KOLK_INFILTRATIE" 150 0.18 "CONTINUOUS" "1812" "G/S")
  (list "3809" "RI-ITR_HULPSTUK_BELUCHTING" 50 0.18 "CONTINUOUS" "1958" "G/S")
  (list "3813" "RI-ITR_HULPSTUK_SCHOONMAAKSTUK" 50 0.18 "CONTINUOUS" "1958" "G/S")
  (list "3815" "RI-ITR_HULPSTUK_VERLOOPSTUK" 50 0.18 "CONTINUOUS" "1958" "G/S")
  (list "3810" "RI-ITR_HULPSTUK_EINDKAP" 50 0.18 "CONTINUOUS" "1958" "G/S")
  (list "3812" "RI-ITR_HULPSTUK_ONTLUCHTING" 50 0.18 "CONTINUOUS" "1958" "G/S")
  (list "3816" "RI-ITR_HULPSTUK_VLINDERKLEP" 50 0.18 "CONTINUOUS" "1958" "G/S")
  (list "3814" "RI-ITR_HULPSTUK_SPUIKRAAN" 50 0.18 "CONTINUOUS" "1958" "G/S")
  (list "3811" "RI-ITR_HULPSTUK_KEERKLEP" 50 0.18 "CONTINUOUS" "1958" "G/S")
  (list "3808" "RI-ITR_HULPSTUK_AFSLUITER" 50 0.18 "CONTINUOUS" "1958" "G/S")
  (list "3840" "RI-ITR_RIOOLPUT-OPHOOGTEBRENGEN" 50 0.18 "RI-OPHOOGTEBRENGEN-SO" "1989" "G/S")
  (list "2011" "RI-ITR_RIOOLPUT_VALPUT" 50 0.18 "CONTINUOUS" "1989" "G/S")
  (list "3843" "RI-ITR_RIOOLPUT-VOLZANDEN" 50 0.18 "CONTINUOUS" "1989" "G/S")
  (list "3839" "RI-ITR_RIOOLPUT_METSELWERK" 50 0.18 "CONTINUOUS" "1989" "G/S")
  (list "4059" "RI-ITR_RIOOLPUT_ZANDVANGPUT" 50 0.18 "CONTINUOUS" "1989" "G/S")
  (list "1991" "RI-ITR_RIOOLPUT_BLINDEPUT" 50 0.18 "CONTINUOUS" "1989" "G/S")
  (list "2005" "RI-ITR_RIOOLPUT_POMPPUT" 50 0.18 "CONTINUOUS" "1989" "G/S")
  (list "4058" "RI-ITR_RIOOLPUT_FILTERPUT" 50 0.18 "CONTINUOUS" "1989" "G/S")
  (list "2008" "RI-ITR_RIOOLPUT_STUWPUT" 50 0.18 "CONTINUOUS" "1989" "G/S")
  (list "2015" "RI-ITR_RIOOLPUT_KRUISINGSPUT" 50 0.18 "CONTINUOUS" "1989" "G/S")
  (list "1996" "RI-ITR_RIOOLPUT_INSPECTIEPUT" 50 0.18 "CONTINUOUS" "1989" "G/S")
  (list "4057" "RI-ITR_RIOOLPUT_DRAINAGEPUT" 50 0.18 "CONTINUOUS" "1989" "G/S")
  (list "3841" "RI-ITR_RIOOLPUT-LINING" 50 0.18 "RI-LINING-SO" "1989" "G/S")
  (list "2002" "RI-ITR_RIOOLPUT_OVERSTORTPUT" 50 0.18 "CONTINUOUS" "1989" "G/S")
  (list "3842" "RI-ITR_RIOOLPUT-VOLSCHUIMEN" 50 0.18 "CONTINUOUS" "1989" "G/S")
  (list "1994" "RI-ITR_RIOOLPUT_HONDEHOKPUT" 50 0.18 "CONTINUOUS" "1989" "G/S")
  (list "3837" "RI-ITR_RIOOLPUT_BETON" 50 0.18 "CONTINUOUS" "1989" "G/S")
  (list "3838" "RI-ITR_RIOOLPUT_KUNSTSTOF" 50 0.18 "CONTINUOUS" "1989" "G/S")
  (list "1965" "RI-ITR_KOLK_TROTTOIRKOLK" 50 0.18 "CONTINUOUS" "1961" "G/S")
  (list "1962" "RI-ITR_KOLK_COMBIKOLK" 50 0.18 "CONTINUOUS" "1961" "G/S")
  (list "3818" "RI-ITR_KOLK-OPHOOGTEBRENGEN" 50 0.18 "RI-OPHOOGTEBRENGEN-SO" "1961" "G/S")
  (list "1963" "RI-ITR_KOLK_RWSKOLK" 50 0.18 "CONTINUOUS" "1961" "G/S")
  (list "3817" "RI-ITR_KOLK_INFILTRATIE" 50 0.18 "CONTINUOUS" "1961" "G/S")
  (list "1964" "RI-ITR_KOLK_STRAATKOLK" 50 0.18 "CONTINUOUS" "1961" "G/S")
  (list "1999" "RI-ITR_AANSLUITPUT_ONTSTOPPINGSPUT" 50 0.18 "CONTINUOUS" "3836" "G/S")
  (list "3931" "RI-DWA_HULPSTUK_AFSLUITER" 20 0.18 "CONTINUOUS" "2241" "G/S")
  (list "3933" "RI-DWA_HULPSTUK_EINDKAP" 20 0.18 "CONTINUOUS" "2241" "G/S")
  (list "3938" "RI-DWA_HULPSTUK_VERLOOPSTUK" 20 0.18 "CONTINUOUS" "2241" "G/S")
  (list "3939" "RI-DWA_HULPSTUK_VLINDERKLEP" 20 0.18 "CONTINUOUS" "2241" "G/S")
  (list "3936" "RI-DWA_HULPSTUK_SCHOONMAAKSTUK" 20 0.18 "CONTINUOUS" "2241" "G/S")
  (list "3932" "RI-DWA_HULPSTUK_BELUCHTING" 20 0.18 "CONTINUOUS" "2241" "G/S")
  (list "3935" "RI-DWA_HULPSTUK_ONTLUCHTING" 20 0.18 "CONTINUOUS" "2241" "G/S")
  (list "3937" "RI-DWA_HULPSTUK_SPUIKRAAN" 20 0.18 "CONTINUOUS" "2241" "G/S")
  (list "3934" "RI-DWA_HULPSTUK_KEERKLEP" 20 0.18 "CONTINUOUS" "2241" "G/S")
  (list "2252" "RI-DWA_RIOOLPUT_BLINDEPUT" 20 0.18 "CONTINUOUS" "2250" "G/S")
  (list "2266" "RI-DWA_RIOOLPUT_OVERSTORTPUT" 20 0.18 "CONTINUOUS" "2250" "G/S")
  (list "2277" "RI-DWA_RIOOLPUT_VALPUT" 20 0.18 "CONTINUOUS" "2250" "G/S")
  (list "4003" "RI-DWA_RIOOLPUT-LINING" 20 0.18 "RI-LINING-SO" "2250" "G/S")
  (list "4005" "RI-DWA_RIOOLPUT-VOLZANDEN" 20 0.18 "CONTINUOUS" "2250" "G/S")
  (list "4008" "RI-DWA_RIOOLPUT_LOZINGSPUT" 20 0.18 "CONTINUOUS" "2250" "G/S")
  (list "4012" "RI-DWA_RIOOLPUT_WERVELPUT" 20 0.18 "CONTINUOUS" "2250" "G/S")
  (list "4004" "RI-DWA_RIOOLPUT-VOLSCHUIMEN" 20 0.18 "CONTINUOUS" "2250" "G/S")
  (list "2260" "RI-DWA_RIOOLPUT_MONSTERNAMEPUT" 20 0.18 "CONTINUOUS" "2250" "G/S")
  (list "4007" "RI-DWA_RIOOLPUT_DOORSPOELPUT" 20 0.18 "CONTINUOUS" "2250" "G/S")
  (list "4011" "RI-DWA_RIOOLPUT_VERDIEPTEPUT" 20 0.18 "CONTINUOUS" "2250" "G/S")
  (list "4013" "RI-DWA_RIOOLPUT_ZINKERPUT" 20 0.18 "CONTINUOUS" "2250" "G/S")
  (list "2269" "RI-DWA_RIOOLPUT_POMPPUT" 20 0.18 "CONTINUOUS" "2250" "G/S")
  (list "3999" "RI-DWA_RIOOLPUT_BETON" 20 0.18 "CONTINUOUS" "2250" "G/S")
  (list "4000" "RI-DWA_RIOOLPUT_KUNSTSTOF" 20 0.18 "CONTINUOUS" "2250" "G/S")
  (list "2257" "RI-DWA_RIOOLPUT_INSPECTIEPUT" 20 0.18 "CONTINUOUS" "2250" "G/S")
  (list "2280" "RI-DWA_RIOOLPUT_ZANDVANGPUT" 20 0.18 "CONTINUOUS" "2250" "G/S")
  (list "4010" "RI-DWA_RIOOLPUT_VERDEKTEPUT" 20 0.18 "CONTINUOUS" "2250" "G/S")
  (list "4009" "RI-DWA_RIOOLPUT_PUTBUIS" 20 0.18 "CONTINUOUS" "2250" "G/S")
  (list "2274" "RI-DWA_RIOOLPUT_STUWPUT" 20 0.18 "CONTINUOUS" "2250" "G/S")
  (list "4002" "RI-DWA_RIOOLPUT-OPHOOGTEBRENGEN" 20 0.18 "RI-OPHOOGTEBRENGEN-SO" "2250" "G/S")
  (list "4001" "RI-DWA_RIOOLPUT_METSELWERK" 20 0.18 "CONTINUOUS" "2250" "G/S")
  (list "2283" "RI-DWA_RIOOLPUT_KRUISINGSPUT" 20 0.18 "CONTINUOUS" "2250" "G/S")
  (list "4015" "RI-DWA_LOZEPUT_VOLGESCHUIMD" 20 0.18 "CONTINUOUS" "4014" "G/S")
  (list "4016" "RI-DWA_LOZEPUT_VOLGEZAND" 20 0.18 "CONTINUOUS" "4014" "G/S")
  (list "2263" "RI-DWA_AANSLUITPUT_ONTSTOPPINGSPUT" 20 0.18 "CONTINUOUS" "3998" "G/S")
  (list "3910" "RI-VACUUMLEIDING_HULPSTUK_VERLOOPSTUK" 10 0.18 "CONTINUOUS" "2208" "G/S")
  (list "3907" "RI-VACUUMLEIDING_HULPSTUK_ONTLUCHTING" 10 0.18 "CONTINUOUS" "2208" "G/S")
  (list "3904" "RI-VACUUMLEIDING_HULPSTUK_BELUCHTING" 10 0.18 "CONTINUOUS" "2208" "G/S")
  (list "3909" "RI-VACUUMLEIDING_HULPSTUK_SPUIKRAAN" 10 0.18 "CONTINUOUS" "2208" "G/S")
  (list "3905" "RI-VACUUMLEIDING_HULPSTUK_EINDKAP" 10 0.18 "CONTINUOUS" "2208" "G/S")
  (list "3903" "RI-VACUUMLEIDING_HULPSTUK_AFSLUITER" 10 0.18 "CONTINUOUS" "2208" "G/S")
  (list "3906" "RI-VACUUMLEIDING_HULPSTUK_KEERKLEP" 10 0.18 "CONTINUOUS" "2208" "G/S")
  (list "3908" "RI-VACUUMLEIDING_HULPSTUK_SCHOONMAAKSTUK" 10 0.18 "CONTINUOUS" "2208" "G/S")
  (list "3911" "RI-VACUUMLEIDING_HULPSTUK_VLINDERKLEP" 10 0.18 "CONTINUOUS" "2208" "G/S")
  (list "2216" "RI-VACUUMLEIDING_RIOOLPUT_POMPPUT" 10 0.18 "CONTINUOUS" "2214" "G/S")
  (list "3921" "RI-VACUUMLEIDING_RIOOLPUT-VOLSCHUIMEN" 10 0.18 "RI-VOLSCHUIMEN-SO" "2214" "G/S")
  (list "3922" "RI-VACUUMLEIDING_RIOOLPUT-VOLZANDEN" 10 0.18 "RI-VOLZANDEN-SO" "2214" "G/S")
  (list "3916" "RI-VACUUMLEIDING_RIOOLPUT_BETON" 10 0.18 "CONTINUOUS" "2214" "G/S")
  (list "3919" "RI-VACUUMLEIDING_RIOOLPUT-OPHOOGTEBRENGEN" 10 0.18 "RI-OPHOOGTEBRENGEN-SO" "2214" "G/S")
  (list "3917" "RI-VACUUMLEIDING_RIOOLPUT_KUNSTSTOF" 10 0.18 "CONTINUOUS" "2214" "G/S")
  (list "3920" "RI-VACUUMLEIDING_RIOOLPUT-LINING" 10 0.18 "RI-LINING-SO" "2214" "G/S")
  (list "2217" "RI-VACUUMLEIDING_RIOOLPUT_STUWPUT" 10 0.18 "CONTINUOUS" "2214" "G/S")
  (list "3918" "RI-VACUUMLEIDING_RIOOLPUT_METSELWERK" 10 0.18 "CONTINUOUS" "2214" "G/S")
  (list "3862" "RI-PERSLEIDING_RIOOLPUT-VOLSCHUIMEN" 210 0.18 "RI-VOLSCHUIMEN-SO" "2074" "G/S")
  (list "3860" "RI-PERSLEIDING_RIOOLPUT-OPHOOGTEBRENGEN" 210 0.18 "RI-OPHOOGTEBRENGEN-SO" "2074" "G/S")
  (list "2077" "RI-PERSLEIDING_RIOOLPUT_STUWPUT" 210 0.18 "CONTINUOUS" "2074" "G/S")
  (list "3863" "RI-PERSLEIDING_RIOOLPUT-VOLZANDEN" 210 0.18 "RI-VOLZANDEN-SO" "2074" "G/S")
  (list "3861" "RI-PERSLEIDING_RIOOLPUT-LINING" 210 0.18 "RI-LINING-SO" "2074" "G/S")
  (list "3858" "RI-PERSLEIDING_RIOOLPUT_KUNSTSTOF" 210 0.18 "CONTINUOUS" "2074" "G/S")
  (list "3859" "RI-PERSLEIDING_RIOOLPUT_METSELWERK" 210 0.18 "CONTINUOUS" "2074" "G/S")
  (list "2076" "RI-PERSLEIDING_RIOOLPUT_POMPPUT" 210 0.18 "CONTINUOUS" "2074" "G/S")
  (list "3857" "RI-PERSLEIDING_RIOOLPUT_BETON" 210 0.18 "CONTINUOUS" "2074" "G/S")
  (list "3848" "RI-PERSLEIDING_HULPSTUK_AFSLUITER" 210 0.18 "CONTINUOUS" "2068" "G/S")
  (list "3852" "RI-PERSLEIDING_HULPSTUK_ONTLUCHTING" 210 0.18 "CONTINUOUS" "2068" "G/S")
  (list "3855" "RI-PERSLEIDING_HULPSTUK_VERLOOPSTUK" 210 0.18 "CONTINUOUS" "2068" "G/S")
  (list "3853" "RI-PERSLEIDING_HULPSTUK_SCHOONMAAKSTUK" 210 0.18 "CONTINUOUS" "2068" "G/S")
  (list "3850" "RI-PERSLEIDING_HULPSTUK_EINDKAP" 210 0.18 "CONTINUOUS" "2068" "G/S")
  (list "3856" "RI-PERSLEIDING_HULPSTUK_VLINDERKLEP" 210 0.18 "CONTINUOUS" "2068" "G/S")
  (list "3851" "RI-PERSLEIDING_HULPSTUK_KEERKLEP" 210 0.18 "CONTINUOUS" "2068" "G/S")
  (list "3854" "RI-PERSLEIDING_HULPSTUK_SPUIKRAAN" 210 0.18 "CONTINUOUS" "2068" "G/S")
  (list "3849" "RI-PERSLEIDING_HULPSTUK_BELUCHTING" 210 0.18 "CONTINUOUS" "2068" "G/S")
  (list "3610" "RI-GWA_KOLK-OPHOOGTEBRENGEN" 30 0.18 "RI-OPHOOGTEBRENGEN-SO" "1685" "G/S")
  (list "1687" "RI-GWA_KOLK_RWSKOLK" 30 0.18 "CONTINUOUS" "1685" "G/S")
  (list "1688" "RI-GWA_KOLK_STRAATKOLK" 30 0.18 "CONTINUOUS" "1685" "G/S")
  (list "3609" "RI-GWA_KOLK_INFILTRATIE" 30 0.18 "CONTINUOUS" "1685" "G/S")
  (list "1686" "RI-GWA_KOLK_COMBIKOLK" 30 0.18 "CONTINUOUS" "1685" "G/S")
  (list "1689" "RI-GWA_KOLK_TROTTOIRKOLK" 30 0.18 "CONTINUOUS" "1685" "G/S")
  (list "1716" "RI-GWA_RIOOLPUT_OVERSTORTPUT" 30 0.18 "CONTINUOUS" "1703" "G/S")
  (list "3673" "RI-GWA_RIOOLPUT-VOLZANDEN" 30 0.18 "CONTINUOUS" "1703" "G/S")
  (list "3679" "RI-GWA_RIOOLPUT_DOORSPOELPUT" 30 0.18 "CONTINUOUS" "1703" "G/S")
  (list "1710" "RI-GWA_RIOOLPUT_INSPECTIEPUT" 30 0.18 "CONTINUOUS" "1703" "G/S")
  (list "1719" "RI-GWA_RIOOLPUT_POMPPUT" 30 0.18 "CONTINUOUS" "1703" "G/S")
  (list "1705" "RI-GWA_RIOOLPUT_BLINDEPUT" 30 0.18 "CONTINUOUS" "1703" "G/S")
  (list "3678" "RI-GWA_RIOOLPUT_METSELWERK" 30 0.18 "CONTINUOUS" "1703" "G/S")
  (list "3670" "RI-GWA_RIOOLPUT-OPHOOGTEBRENGEN" 30 0.18 "RI-OPHOOGTEBRENGEN-SO" "1703" "G/S")
  (list "1729" "RI-GWA_RIOOLPUT_KRUISINGSPUT" 30 0.18 "CONTINUOUS" "1703" "G/S")
  (list "3671" "RI-GWA_RIOOLPUT-LINING" 30 0.18 "RI-LINING-SO" "1703" "G/S")
  (list "3683" "RI-GWA_RIOOLPUT_VERDIEPTEPUT" 30 0.18 "CONTINUOUS" "1703" "G/S")
  (list "3682" "RI-GWA_RIOOLPUT_VERDEKTEPUT" 30 0.18 "CONTINUOUS" "1703" "G/S")
  (list "1722" "RI-GWA_RIOOLPUT_STUWPUT" 30 0.18 "CONTINUOUS" "1703" "G/S")
  (list "3684" "RI-GWA_RIOOLPUT_WERVELPUT" 30 0.18 "CONTINUOUS" "1703" "G/S")
  (list "3677" "RI-GWA_RIOOLPUT_KUNSTSTOF" 30 0.18 "CONTINUOUS" "1703" "G/S")
  (list "1725" "RI-GWA_RIOOLPUT_VALPUT" 30 0.18 "CONTINUOUS" "1703" "G/S")
  (list "3685" "RI-GWA_RIOOLPUT_ZINKERPUT" 30 0.18 "CONTINUOUS" "1703" "G/S")
  (list "3680" "RI-GWA_RIOOLPUT_LOZINGSPUT" 30 0.18 "CONTINUOUS" "1703" "G/S")
  (list "3676" "RI-GWA_RIOOLPUT_BETON" 30 0.18 "CONTINUOUS" "1703" "G/S")
  (list "3681" "RI-GWA_RIOOLPUT_PUTBUIS" 30 0.18 "CONTINUOUS" "1703" "G/S")
  (list "3672" "RI-GWA_RIOOLPUT-VOLSCHUIMEN" 30 0.18 "CONTINUOUS" "1703" "G/S")
  (list "1713" "RI-GWA_AANSLUITPUT_ONTSTOPPINGSPUT" 30 0.18 "CONTINUOUS" "3675" "G/S")
  (list "3603" "RI-GWA_HULPSTUK_KEERKLEP" 30 0.18 "CONTINUOUS" "1681" "G/S")
  (list "3605" "RI-GWA_HULPSTUK_SCHOONMAAKSTUK" 30 0.18 "CONTINUOUS" "1681" "G/S")
  (list "3606" "RI-GWA_HULPSTUK_SPUIKRAAN" 30 0.18 "CONTINUOUS" "1681" "G/S")
  (list "3602" "RI-GWA_HULPSTUK_EINDKAP" 30 0.18 "CONTINUOUS" "1681" "G/S")
  (list "3604" "RI-GWA_HULPSTUK_ONTLUCHTING" 30 0.18 "CONTINUOUS" "1681" "G/S")
  (list "1684" "RI-GWA_HULPSTUK_ONTSTOPPINGSSTUK" 30 0.18 "CONTINUOUS" "1681" "G/S")
  (list "3601" "RI-GWA_HULPSTUK_BELUCHTING" 30 0.18 "CONTINUOUS" "1681" "G/S")
  (list "1683" "RI-GWA_HULPSTUK_INLAAT" 30 0.18 "CONTINUOUS" "1681" "G/S")
  (list "3607" "RI-GWA_HULPSTUK_VERLOOPSTUK" 30 0.18 "CONTINUOUS" "1681" "G/S")
  (list "3608" "RI-GWA_HULPSTUK_VLINDERKLEP" 30 0.18 "CONTINUOUS" "1681" "G/S")
  (list "3600" "RI-GWA_HULPSTUK_AFSLUITER" 30 0.18 "CONTINUOUS" "1681" "G/S")
  (list "3688" "RI-GWA_LOZEPUT_VOLGEZAND" 30 0.18 "CONTINUOUS" "3686" "G/S")
  (list "3687" "RI-GWA_LOZEPUT_VOLGESCHUIMD" 30 0.18 "CONTINUOUS" "3686" "G/S")
  (list "1657" "RI-DRAINAGE_PUT_DOORSPUITPUT" 90 0.18 "CONTINUOUS" "1656" "G/S")
  (list "3593" "RI-DRAINAGE_PUT_DRAINAGEPUT" 90 0.18 "CONTINUOUS" "1656" "G/S")
  (list "3497" "RI-DRAINAGE_PUT_BLINDEPUT" 90 0.18 "CONTINUOUS" "1656" "G/S")
  (list "3589" "RI-DRAINAGE_HULPSTUK_SPUIKRAAN" 90 0.18 "CONTINUOUS" "1653" "G/S")
  (list "3491" "RI-DRAINAGE_HULPSTUK_INLAAT" 90 0.18 "CONTINUOUS" "1653" "G/S")
  (list "3590" "RI-DRAINAGE_HULPSTUK_VERLOOPSTUK" 90 0.18 "CONTINUOUS" "1653" "G/S")
  (list "3588" "RI-DRAINAGE_HULPSTUK_SCHOONMAAKSTUK" 90 0.18 "CONTINUOUS" "1653" "G/S")
  (list "3585" "RI-DRAINAGE_HULPSTUK_KEERKLEP" 90 0.18 "CONTINUOUS" "1653" "G/S")
  (list "3582" "RI-DRAINAGE_HULPSTUK_AFSLUITER" 90 0.18 "CONTINUOUS" "1653" "G/S")
  (list "3587" "RI-DRAINAGE_HULPSTUK_ONTSTOPPINGSSTUK" 90 0.18 "CONTINUOUS" "1653" "G/S")
  (list "3584" "RI-DRAINAGE_HULPSTUK_EINDKAP" 90 0.18 "CONTINUOUS" "1653" "G/S")
  (list "3583" "RI-DRAINAGE_HULPSTUK_BELUCHTING" 90 0.18 "CONTINUOUS" "1653" "G/S")
  (list "3591" "RI-DRAINAGE_HULPSTUK_VLINDERKLEP" 90 0.18 "CONTINUOUS" "1653" "G/S")
  (list "3586" "RI-DRAINAGE_HULPSTUK_ONTLUCHTING" 90 0.18 "CONTINUOUS" "1653" "G/S")
  (list "3501" "RI-DRAINAGE_HULPSTUK_T STUK" 90 0.18 "CONTINUOUS" "1653" "G/S")
  (list "1837" "RI-HWA_RIOOLPUT_INSPECTIEPUT_HONDEHOKPUT" 150 0.18 "CONTINUOUS" "1839" "G/S")
  (list "3799" "RI-HWA_RIOOLPUT_INSPECTIEPUT_REINIGENDEPUT" 150 0.18 "CONTINUOUS" "1839" "G/S")
  (list "1791" "RI-HWA_GOOT_LIJNGOOT_ZANDVANGER" 150 0.18 "CONTINUOUS" "1790" "G/S")
  (list "4006" "RI-DWA_RIOOLPUT_INSPECTIEPUT_REINIGENDEPUT" 20 0.18 "CONTINUOUS" "2257" "G/S")
  (list "2255" "RI-DWA_RIOOLPUT_INSPECTIEPUT_HONDEHOKPUT" 20 0.18 "CONTINUOUS" "2257" "G/S")
  (list "3674" "RI-GWA_RIOOLPUT_INSPECTIEPUT_REINIGENDEPUT" 30 0.18 "CONTINUOUS" "1710" "G/S")
  (list "1708" "RI-GWA_RIOOLPUT_INSPECTIEPUT_HONDEHOKPUT" 30 0.18 "CONTINUOUS" "1710" "G/S")
  (list "3045" "RI-MATERIAAL" 7 0.18 "CONTINUOUS" "" "G/S")
  (list "1634" "RI-BOB" 90 0.18 "CONTINUOUS" "" "G/S")
  (list "4029" "RI-OVERIG_DUIKER" 10 0.18 "RI-OVERIG-SO" "2052" "G")
  (list "4028" "RI-OVERIG_OVERSTORTLEIDING" 10 0.18 "RI-OVERIG-SO" "2052" "G")
  (list "2193" "RI-OVERIG_TRANSPORTLEIDING" 10 0.18 "RI-TRANSPORTLEIDING-SO" "2052" "G")
  (list "3923" "RI-OVERIG_RIOOLLEIDING" 10 0.18 "RI-TRANSPORTLEIDING-SO" "2052" "G")
  (list "3064" "RI-OVERIG_RIOOLPUT" 10 0.18 "CONTINUOUS" "2052" "G")
  (list "4076" "RI-OVERIG_ZINKER" 10 0.18 "RI-OVERIG-SO" "2052" "G")
  (list "4075" "RI-OVERIG_WEESLEIDING" 10 0.18 "RI-OVERIG-SO" "2052" "G")
  (list "4061" "RI-OVERIG_BERGBEZINKLEIDING" 10 0.18 "RI-OVERIG-SO" "2052" "G")
  (list "4071" "RI-OVERIG_GEBOORDELEIDING" 10 0.18 "RI-OVERIG-SO" "2052" "G")
  (list "2341" "RI-OVERIG_LOZELEIDING" 10 0.18 "RI-LOZELEIDING-SO" "2052" "G")
  (list "4062" "RI-OVERIG_BERGINGSLEIDING" 10 0.18 "RI-OVERIG-SO" "2052" "G")
  (list "2053" "RI-OVERIG_PERCEELAANSLUITLEIDING" 10 0.18 "RI-AANSLUITLEIDING-SO" "2052" "G")
  (list "4073" "RI-OVERIG_ONTLUCHTINGSLEIDING" 10 0.18 "RI-OVERIG-SO" "2052" "G")
  (list "2051" "RI-OVERIG_MANTELBUIS" 10 0.18 "CONTINUOUS" "2052" "G")
  (list "4063" "RI-OVERIG_BLUSRIOOL" 10 0.18 "RI-OVERIG-SO" "2052" "G")
  (list "1860" "RI-HWA_TRANSPORTLEIDING" 150 0.18 "RI-HWA-SO" "1786" "G")
  (list "1817" "RI-HWA_KOLKAANSLUITLEIDING" 150 0.18 "RI-HWA_AANSLUITLEIDING-SO" "1786" "G")
  (list "3805" "RI-HWA_LOZELEIDING" 150 0.18 "RI-LOZELEIDING-SO" "1786" "G")
  (list "1795" "RI-HWA_PERCEELAANSLUITLEIDING" 150 0.18 "RI-HWA_AANSLUITLEIDING-SO" "1786" "G")
  (list "1789" "RI-HWA_GOOT" 150 0.18 "CONTINUOUS" "1786" "G")
  (list "1826" "RI-HWA_LOZINGSPUNT" 150 0.18 "CONTINUOUS" "1786" "G")
  (list "1827" "RI-HWA_MANTELBUIS" 150 0.18 "CONTINUOUS" "1786" "G")
  (list "3710" "RI-HWA_RIOOLLEIDING" 150 0.18 "RI-HWA-SO" "1786" "G")
  (list "1829" "RI-HWA_PERCEELAANSLUITPUNT" 150 0.18 "CONTINUOUS" "1786" "G")
  (list "4060" "RI-ITR_TRANSPORTLEIDING" 50 0.18 "RI-ITR-SO" "1944" "G")
  (list "3821" "RI-ITR_RESERVOIR" 50 0.18 "CONTINUOUS" "1944" "G")
  (list "2049" "RI-ITR_LOZELEIDING" 50 0.18 "RI-LOZELEIDING-SO" "1944" "G")
  (list "1966" "RI-ITR_KOLKAANSLUITLEIDING" 50 0.18 "RI-ITR_AANSLUITLEIDING-SO" "1944" "G")
  (list "1975" "RI-ITR_LOZINGSPUNT" 50 0.18 "CONTINUOUS" "1944" "G")
  (list "1976" "RI-ITR_MANTELBUIS" 50 0.18 "CONTINUOUS" "1944" "G")
  (list "2017" "RI-ITR_RIOOLLEIDING" 50 0.18 "RI-ITR-SO" "1944" "G")
  (list "1948" "RI-ITR_PERCEELAANSLUITLEIDING" 50 0.18 "RI-ITR_AANSLUITLEIDING-SO" "1944" "G")
  (list "3468" "RI-RWZI_CIRCULATIELEIDING" 70 0.18 "RI-RWZI_CIRCULATIELEIDING-SO" "3451" "G")
  (list "3457" "RI-RWZI_DOCEERLEIDING" 210 0.18 "RI-RWZI_DOCEERLEIDING-SO" "3451" "G")
  (list "3467" "RI-RWZI_KORTSLUITLEIDING" 100 0.18 "RI-RWZI_KORTSLUITLEIDING-SO" "3451" "G")
  (list "3459" "RI-RWZI_TERREINWATERLEIDING" 120 0.18 "RI-RWZI_TERREINWATERLEIDING-SO" "3451" "G")
  (list "3464" "RI-RWZI_INGEDIKTSLIBLEIDING" 200 0.18 "RI-RWZI_INGEDIKTSLIBLEIDING-SO" "3451" "G")
  (list "3460" "RI-RWZI_RECIRCULATIELEIDING" 60 0.18 "RI-RWZI_RECIRCULATIELEIDING-SO" "3451" "G")
  (list "3458" "RI-RWZI_LUCHTLEIDING" 7 0.18 "RI-RWZI_LUCHTLEIDING-SO" "3451" "G")
  (list "3466" "RI-RWZI_HOOFDPROCESLEIDING" 110 0.18 "RI-RWZI_HOOFDPROCESLEIDING-SO" "3451" "G")
  (list "3463" "RI-RWZI_DRIJFLEIDING" 170 0.18 "RI-RWZI_DRIJFLEIDING-SO" "3451" "G")
  (list "3465" "RI-RWZI_IJZERCHLORIDELEIDING" 130 0.18 "RI-RWZI_IJZERCHLORIDELEIDING-SO" "3451" "G")
  (list "3456" "RI-RWZI_SLIBLEIDING" 40 0.18 "RI-RWZI_SLIBLEIDING-SO" "3451" "G")
  (list "3453" "RI-RWZI_PROCESLEIDING" 30 0.18 "RI-RWZI_PROCESLEIDING-SO" "3451" "G")
  (list "3469" "RI-RWZI_CONDENSAATLEIDING" 150 0.18 "RI-RWZI_CONDENSAATLEIDING-SO" "3451" "G")
  (list "3455" "RI-RWZI_EFFLUENTIELEIDING" 90 0.18 "RI-RWZI_EFFLUENTIELEIDING-SO" "3451" "G")
  (list "3454" "RI-RWZI_INFLUENTIELEIDING" 50 0.18 "RI-RWZI_INFLUENTIELEIDING-SO" "3451" "G")
  (list "3461" "RI-RWZI_RETOURSLIBLEIDING" 180 0.18 "RI-RWZI_RETOURSLIBLEIDING-SO" "3451" "G")
  (list "3462" "RI-RWZI_SURPLUSSLEIDING" 190 0.18 "RI-RWZI_SURPLUSSLEIDING-SO" "3451" "G")
  (list "3452" "RI-RWZI_TERREINRIOLERING" 10 0.18 "RI-RWZI_TERREINRIOLERING-SO" "3451" "G")
  (list "3940" "RI-DWA_RIOOLLEIDING" 20 0.18 "RI-DWA-SO" "2220" "G")
  (list "2227" "RI-DWA_PERCEELAANSLUITLEIDING" 20 0.18 "RI-DWA_AANSLUITLEIDING-SO" "2220" "G")
  (list "2286" "RI-DWA_TRANSPORTLEIDING" 20 0.18 "RI-DWA-SO" "2220" "G")
  (list "2340" "RI-DWA_LOZELEIDING" 20 0.18 "RI-LOZELEIDING-SO" "2220" "G")
  (list "4041" "RI-DWA_KOLKAANSLUITLEIDING" 20 0.18 "RI-DWA-SO" "2220" "G")
  (list "2247" "RI-DWA_PERCEELAANSLUITPUNT" 20 0.18 "CONTINUOUS" "2220" "G")
  (list "2245" "RI-DWA_MANTELBUIS" 20 0.18 "CONTINUOUS" "2220" "G")
  (list "2244" "RI-DWA_IBA" 20 0.18 "CONTINUOUS" "2220" "G")
  (list "2201" "RI-VACUUMLEIDING_500" 10 0.18 "RI-VACUUM-SO" "2194" "G")
  (list "2203" "RI-VACUUMLEIDING_630" 10 0.18 "RI-VACUUM-SO" "2194" "G")
  (list "3914" "RI-VACUUMLEIDING-VOLSCHUIMEN" 10 0.18 "RI-VOLSCHUIMEN-SO" "2194" "G")
  (list "2199" "RI-VACUUMLEIDING_400" 10 0.18 "RI-VACUUM-SO" "2194" "G")
  (list "2211" "RI-VACUUMLEIDING_MANTELBUIS" 10 0.18 "CONTINUOUS" "2194" "G")
  (list "2197" "RI-VACUUMLEIDING_315" 10 0.18 "RI-VACUUM-SO" "2194" "G")
  (list "3912" "RI-VACUUMLEIDING-OPHOOGTEBRENGEN" 10 0.18 "RI-OPHOOGTEBRENGEN-SO" "2194" "G")
  (list "3915" "RI-VACUUMLEIDING-VOLZANDEN" 10 0.18 "RI-VOLZANDEN-SO" "2194" "G")
  (list "2200" "RI-VACUUMLEIDING_450" 10 0.18 "RI-VACUUM-SO" "2194" "G")
  (list "2196" "RI-VACUUMLEIDING_250" 10 0.18 "RI-VACUUM-SO" "2194" "G")
  (list "2195" "RI-VACUUMLEIDING_160" 10 0.18 "RI-VACUUM-SO" "2194" "G")
  (list "2202" "RI-VACUUMLEIDING_560" 10 0.18 "RI-VACUUM-SO" "2194" "G")
  (list "3913" "RI-VACUUMLEIDING-LINING" 10 0.18 "RI-LINING-SO" "2194" "G")
  (list "2198" "RI-VACUUMLEIDING_355" 10 0.18 "RI-VACUUM-SO" "2194" "G")
  (list "2071" "RI-PERSLEIDING_MANTELBUIS" 210 0.18 "CONTINUOUS" "2054" "G")
  (list "4082" "RI-PERSLEIDING_PERCEELAANSLUITLEIDING" 210 0.18 "RI-PERS-SO" "2054" "G")
  (list "2062" "RI-PERSLEIDING_560" 210 0.18 "RI-PERS-SO" "2054" "G")
  (list "2061" "RI-PERSLEIDING_500" 210 0.18 "RI-PERS-SO" "2054" "G")
  (list "2059" "RI-PERSLEIDING_400" 210 0.18 "RI-PERS-SO" "2054" "G")
  (list "2063" "RI-PERSLEIDING_630" 210 0.18 "RI-PERS-SO" "2054" "G")
  (list "2988" "RI-PERSLEIDING_63" 210 0.18 "RI-PERS-SO" "2054" "G")
  (list "2060" "RI-PERSLEIDING_450" 210 0.18 "RI-PERS-SO" "2054" "G")
  (list "2055" "RI-PERSLEIDING_160" 210 0.18 "RI-PERS-SO" "2054" "G")
  (list "4077" "RI-PERSLEIDING_LOZELEIDING" 210 0.18 "RI-LOZELEIDING-SO" "2054" "G")
  (list "2989" "RI-PERSLEIDING_90" 210 0.18 "RI-PERS-SO" "2054" "G")
  (list "2058" "RI-PERSLEIDING_355" 210 0.18 "RI-PERS-SO" "2054" "G")
  (list "2057" "RI-PERSLEIDING_315" 210 0.18 "RI-PERS-SO" "2054" "G")
  (list "4084" "RI-PERSLEIDING_ZINKER" 210 0.18 "RI-PERS-SO" "2054" "G")
  (list "2990" "RI-PERSLEIDING_110" 210 0.18 "RI-PERS-SO" "2054" "G")
  (list "2056" "RI-PERSLEIDING_250" 210 0.18 "RI-PERS-SO" "2054" "G")
  (list "1784" "RI-GWA_LOZELEIDING" 30 0.18 "RI-LOZELEIDING-SO" "1664" "G")
  (list "1731" "RI-GWA_TRANSPORTLEIDING" 30 0.18 "RI-GWA-SO" "1664" "G")
  (list "3613" "RI-GWA_RIOOLLEIDING" 30 0.18 "RI-GWA-SO" "1664" "G")
  (list "1699" "RI-GWA_LOZINGSPUNT" 30 0.18 "CONTINUOUS" "1664" "G")
  (list "1667" "RI-GWA_PERCEELAANSLUITLEIDING" 30 0.18 "RI-GWA_AANSLUITLEIDING-SO" "1664" "G")
  (list "1690" "RI-GWA_KOLKAANSLUITLEIDING" 30 0.18 "RI-GWA_AANSLUITLEIDING-SO" "1664" "G")
  (list "1700" "RI-GWA_MANTELBUIS" 30 0.18 "CONTINUOUS" "1664" "G")
  (list "1638" "RI-DRAINAGE_DRAIN" 90 0.18 "RI-DRAINAGE-SO" "1635" "G")
  (list "3598" "RI-DRAINAGE_LOZELEIDING" 90 0.18 "CONTINUOUS" "1635" "G")
  (list "4040" "RI-DRAINAGE_TRANSPORTLEIDING" 90 0.18 "RI-DRAINAGE-SO" "1635" "G")
  (list "3489" "RI-DRAINAGE_PERCEELAANSLUITLEIDING" 90 0.18 "CONTINUOUS" "1635" "G")
  (list "4039" "RI-DRAINAGE_MANTELBUIS" 90 0.18 "CONTINUOUS" "1635" "G")
  (list "3581" "RI-DRAINAGE_KOLKAANSLUITLEIDING" 90 0.18 "CONTINUOUS" "1635" "G")
  (list "1654" "RI-DRAINAGE_LOZINGSPUNT" 90 0.18 "CONTINUOUS" "1635" "G")
  (list "4064" "RI-OVERIG_DUIKER_KOLKAANSLUITLEIDING" 10 0.18 "RI-AANSLUITLEIDING-SO" "4029" "G")
  (list "4065" "RI-OVERIG_DUIKER_LOZELEIDING" 10 0.18 "RI-LOZELEIDING-SO" "4029" "G")
  (list "4069" "RI-OVERIG_DUIKER_PERCEELAANSLUITLEIDING" 10 0.18 "RI-AANSLUITLEIDING-SO" "4029" "G")
  (list "4068" "RI-OVERIG_DUIKER_MANTELBUIS" 10 0.18 "CONTINUOUS" "4029" "G")
  (list "4070" "RI-OVERIG_DUIKER_STUWLEIDING" 10 0.18 "RI-OVERIG-SO" "4029" "G")
  (list "3902" "RI-OVERIG_TRANSPORTLEIDING_PVC" 10 0.18 "RI-TRANSPORTLEIDING-SO" "2193" "G")
  (list "3897" "RI-OVERIG_TRANSPORTLEIDING-VOLSCHUIMEN" 10 0.18 "RI-VOLSCHUIMEN-SO" "2193" "G")
  (list "3899" "RI-OVERIG_TRANSPORTLEIDING_BETON" 10 0.18 "RI-TRANSPORTLEIDING-SO" "2193" "G")
  (list "3896" "RI-OVERIG_TRANSPORTLEIDING-LINING" 10 0.18 "RI-LINING-SO" "2193" "G")
  (list "3898" "RI-OVERIG_TRANSPORTLEIDING-VOLZANDEN" 10 0.18 "RI-VOLZANDEN-SO" "2193" "G")
  (list "3895" "RI-OVERIG_TRANSPORTLEIDING-OPHOOGTEBRENGEN" 10 0.18 "RI-OPHOOGTEBRENGEN-SO" "2193" "G")
  (list "3900" "RI-OVERIG_TRANSPORTLEIDING_GRES" 10 0.18 "RI-TRANSPORTLEIDING-SO" "2193" "G")
  (list "3901" "RI-OVERIG_TRANSPORTLEIDING_PE" 10 0.18 "RI-TRANSPORTLEIDING-SO" "2193" "G")
  (list "2219" "RI-OVERIG_RIOOLLEIDING-VOLSCHUIMEN" 10 0.18 "RI-VOLSCHUIMEN-SO" "3923" "G")
  (list "3928" "RI-OVERIG_RIOOLLEIDING_GRES" 10 0.18 "RI-TRANSPORTLEIDING-SO" "3923" "G")
  (list "3926" "RI-OVERIG_RIOOLLEIDING-VOLZANDEN" 10 0.18 "RI-VOLZANDEN-SO" "3923" "G")
  (list "3930" "RI-OVERIG_RIOOLLEIDING_PVC" 10 0.18 "RI-TRANSPORTLEIDING-SO" "3923" "G")
  (list "3924" "RI-OVERIG_RIOOLLEIDING-OPHOOGTEBRENGEN" 10 0.18 "RI-OPHOOGTEBRENGEN-SO" "3923" "G")
  (list "3927" "RI-OVERIG_RIOOLLEIDING_BETON" 10 0.18 "RI-TRANSPORTLEIDING-SO" "3923" "G")
  (list "3929" "RI-OVERIG_RIOOLLEIDING_PE" 10 0.18 "RI-TRANSPORTLEIDING-SO" "3923" "G")
  (list "3925" "RI-OVERIG_RIOOLLEIDING-LINING" 10 0.18 "RI-LINING-SO" "3923" "G")
  (list "4027" "RI-OVERIG_LOZELEIDING_VOLGEZAND" 10 0.18 "RI-VOLZANDEN-SO" "2341" "G")
  (list "4025" "RI-OVERIG_LOZELEIDING_UITLEGGER" 10 0.18 "RI-UITLEGGER-SO" "2341" "G")
  (list "4026" "RI-OVERIG_LOZELEIDING_VOLGESCHUIMD" 10 0.18 "RI-VOLSCHUIMEN-SO" "2341" "G")
  (list "3048" "RI-OVERIG_TANK_PROPAAN" 10 0.18 "CONTINUOUS" "3046" "G")
  (list "3047" "RI-OVERIG_TANK_AARDGAS" 10 0.18 "CONTINUOUS" "3046" "G")
  (list "1896" "RI-HWA_TRANSPORTLEIDING_GVK" 150 0.18 "RI-HWA-SO" "1860" "G")
  (list "1933" "RI-HWA_TRANSPORTLEIDING_PVC" 150 0.18 "RI-HWA-SO" "1860" "G")
  (list "3803" "RI-HWA_TRANSPORTLEIDING-VOLSCHUIMEN" 150 0.18 "RI-VOLSCHUIMEN-SO" "1860" "G")
  (list "1885" "RI-HWA_TRANSPORTLEIDING_GRES" 150 0.18 "RI-HWA-SO" "1860" "G")
  (list "3804" "RI-HWA_TRANSPORTLEIDING-VOLZANDEN" 150 0.18 "RI-VOLZANDEN-SO" "1860" "G")
  (list "1861" "RI-HWA_TRANSPORTLEIDING_BETON" 150 0.18 "RI-HWA-SO" "1860" "G")
  (list "1923" "RI-HWA_TRANSPORTLEIDING_PE" 150 0.18 "RI-HWA-SO" "1860" "G")
  (list "3801" "RI-HWA_TRANSPORTLEIDING-OPHOOGTEBRENGEN" 150 0.18 "RI-OPHOOGTEBRENGEN-SO" "1860" "G")
  (list "3802" "RI-HWA_TRANSPORTLEIDING-LINING" 150 0.18 "RI-LINING-SO" "1860" "G")
  (list "1822" "RI-HWA_KOLKAANSLUITLEIDING_PVC" 150 0.18 "RI-HWA_AANSLUITLEIDING-SO" "1817" "G")
  (list "1818" "RI-HWA_KOLKAANSLUITLEIDING_PE" 150 0.18 "RI-HWA_AANSLUITLEIDING-SO" "1817" "G")
  (list "3806" "RI-HWA_LOZELEIDING_VOLGESCHUIMD" 150 0.18 "RI-VOLSCHUIMEN-SO" "3805" "G")
  (list "1941" "RI-HWA_LOZELEIDING_UITLEGGER" 150 0.18 "RI-UITLEGGER-SO" "3805" "G")
  (list "3807" "RI-HWA_LOZELEIDING_VOLGEZAND" 150 0.18 "RI-VOLZANDEN-SO" "3805" "G")
  (list "1805" "RI-HWA_PERCEELAANSLUITLEIDING_PVC" 150 0.18 "RI-HWA_AANSLUITLEIDING-SO" "1795" "G")
  (list "1796" "RI-HWA_PERCEELAANSLUITLEIDING_GRES" 150 0.18 "RI-HWA_AANSLUITLEIDING-SO" "1795" "G")
  (list "3074" "RI-HWA_PERCEELAANSLUITLEIDING_PP" 150 0.18 "RI-HWA_AANSLUITLEIDING-SO" "1795" "G")
  (list "1800" "RI-HWA_PERCEELAANSLUITLEIDING_PE" 150 0.18 "RI-HWA_AANSLUITLEIDING-SO" "1795" "G")
  (list "1790" "RI-HWA_GOOT_LIJNGOOT" 150 0.18 "CONTINUOUS" "1789" "G")
  (list "3693" "RI-HWA_GOOT_MOLGOOT" 150 0.18 "CONTINUOUS" "1789" "G")
  (list "3694" "RI-HWA_GOOT_TALUDGOOT" 150 0.18 "CONTINUOUS" "1789" "G")
  (list "3695" "RI-HWA_GOOT_VERHOLENGOOT" 150 0.18 "CONTINUOUS" "1789" "G")
  (list "1811" "RI-HWA_HULPSTUK_ONTSTOPPINGSSTUK" 150 0.18 "CONTINUOUS" "1809" "G")
  (list "1810" "RI-HWA_HULPSTUK_INLAAT" 150 0.18 "CONTINUOUS" "1809" "G")
  (list "3709" "RI-HWA_LOZINGSPUNT_OPPERVLAKTEWATER" 150 0.18 "CONTINUOUS" "1826" "G")
  (list "3708" "RI-HWA_LOZINGSPUNT_BODEM" 150 0.18 "CONTINUOUS" "1826" "G")
  (list "3773" "RI-HWA_RIOOLLEIDING_PE" 150 0.18 "RI-HWA-SO" "3710" "G")
  (list "3746" "RI-HWA_RIOOLLEIDING_GVK" 150 0.18 "RI-HWA-SO" "3710" "G")
  (list "3783" "RI-HWA_RIOOLLEIDING_PVC" 150 0.18 "RI-HWA-SO" "3710" "G")
  (list "3711" "RI-HWA_RIOOLLEIDING_BETON" 150 0.18 "RI-HWA-SO" "3710" "G")
  (list "4050" "RI-HWA_RIOOLLEIDING_STUWLEIDING" 150 0.18 "RI-HWA-SO" "3710" "G")
  (list "3735" "RI-HWA_RIOOLLEIDING_GRES" 150 0.18 "RI-HWA-SO" "3710" "G")
  (list "4051" "RI-HWA_RIOOLLEIDING_ZINKER" 150 0.18 "RI-HWA-SO" "3710" "G")
  (list "1960" "RI-ITR_HULPSTUK_ONTSTOPPINGSSTUK" 50 0.18 "CONTINUOUS" "1958" "G")
  (list "1959" "RI-ITR_HULPSTUK_INLAAT" 50 0.18 "CONTINUOUS" "1958" "G")
  (list "3826" "RI-ITR_RESERVOIR_INFILTRATIERESERVOIR" 50 0.18 "CONTINUOUS" "3821" "G")
  (list "3833" "RI-ITR_RESERVOIR_OPENBERGING" 50 0.18 "CONTINUOUS" "3821" "G")
  (list "3825" "RI-ITR_RESERVOIR_BEZINKBASSIN" 50 0.18 "CONTINUOUS" "3821" "G")
  (list "3834" "RI-ITR_RESERVOIR_ZUIVERINGSRESERVOIR" 50 0.18 "CONTINUOUS" "3821" "G")
  (list "3823" "RI-ITR_RESERVOIR_BERGINGSBASSIN" 50 0.18 "CONTINUOUS" "3821" "G")
  (list "3822" "RI-ITR_RESERVOIR_BERGBEZINKBASIN" 50 0.18 "CONTINUOUS" "3821" "G")
  (list "3824" "RI-ITR_RESERVOIR_BERGINGSVIJVER" 50 0.18 "CONTINUOUS" "3821" "G")
  (list "3845" "RI-ITR_LOZELEIDING_UITLEGGER" 50 0.18 "RI-UITLEGGER-SO" "2049" "G")
  (list "3846" "RI-ITR_LOZELEIDING_VOLGESCHUIMD" 50 0.18 "RI-VOLSCHUIMEN-SO" "2049" "G")
  (list "3847" "RI-ITR_LOZELEIDING_VOLGEZAND" 50 0.18 "RI-VOLZANDEN-SO" "2049" "G")
  (list "1967" "RI-ITR_KOLKAANSLUITLEIDING_PE" 50 0.18 "RI-ITR_AANSLUITLEIDING-SO" "1966" "G")
  (list "1971" "RI-ITR_KOLKAANSLUITLEIDING_PVC" 50 0.18 "RI-ITR_AANSLUITLEIDING-SO" "1966" "G")
  (list "3819" "RI-ITR_LOZINGSPUNT_BODEM" 50 0.18 "CONTINUOUS" "1975" "G")
  (list "3820" "RI-ITR_LOZINGSPUNT_OPPERVLAKTEWATER" 50 0.18 "CONTINUOUS" "1975" "G")
  (list "2031" "RI-ITR_RIOOLLEIDING_PE" 50 0.18 "RI-ITR-SO" "2017" "G")
  (list "2018" "RI-ITR_RIOOLLEIDING_BETON" 50 0.18 "RI-ITR-SO" "2017" "G")
  (list "4055" "RI-ITR_RIOOLLEIDING_STUWLEIDING" 50 0.18 "RI-ITR-SO" "2017" "G")
  (list "2041" "RI-ITR_RIOOLLEIDING_PVC" 50 0.18 "RI-ITR-SO" "2017" "G")
  (list "4056" "RI-ITR_RIOOLLEIDING_ZINKER" 50 0.18 "RI-ITR-SO" "2017" "G")
  (list "1954" "RI-ITR_PERCEELAANSLUITLEIDING_PVC" 50 0.18 "RI-ITR_AANSLUITLEIDING-SO" "1948" "G")
  (list "1949" "RI-ITR_PERCEELAANSLUITLEIDING_PE" 50 0.18 "RI-ITR_AANSLUITLEIDING-SO" "1948" "G")
  (list "3969" "RI-DWA_RIOOLLEIDING_GRES" 20 0.18 "RI-DWA-SO" "3940" "G")
  (list "3980" "RI-DWA_RIOOLLEIDING_PE" 20 0.18 "RI-DWA-SO" "3940" "G")
  (list "3990" "RI-DWA_RIOOLLEIDING_PVC" 20 0.18 "RI-DWA-SO" "3940" "G")
  (list "4043" "RI-DWA_RIOOLLEIDING_ZINKER" 20 0.18 "RI-DWA-SO" "3940" "G")
  (list "3941" "RI-DWA_RIOOLLEIDING-OPHOOGTEBRENGEN" 20 0.18 "RI-OPHOOGTEBRENGEN-SO" "3940" "G")
  (list "3942" "RI-DWA_RIOOLLEIDING-LINING" 20 0.18 "RI-LINING-SO" "3940" "G")
  (list "3945" "RI-DWA_RIOOLLEIDING_BETON" 20 0.18 "RI-DWA-SO" "3940" "G")
  (list "3943" "RI-DWA_RIOOLLEIDING-VOLSCHUIMEN" 20 0.18 "RI-VOLSCHUIMEN-SO" "3940" "G")
  (list "3944" "RI-DWA_RIOOLLEIDING-VOLZANDEN" 20 0.18 "RI-VOLZANDEN-SO" "3940" "G")
  (list "4042" "RI-DWA_RIOOLLEIDING_STUWLEIDING" 20 0.18 "RI-DWA-SO" "3940" "G")
  (list "2243" "RI-DWA_HULPSTUK_ONTSTOPPINGSSTUK" 20 0.18 "CONTINUOUS" "2241" "G")
  (list "2242" "RI-DWA_HULPSTUK_INLAAT" 20 0.18 "CONTINUOUS" "2241" "G")
  (list "2223" "RI-DWA_AFSCHEIDER_VET" 20 0.18 "CONTINUOUS" "2221" "G")
  (list "2224" "RI-DWA_AFSCHEIDER_SLIB" 20 0.18 "CONTINUOUS" "2221" "G")
  (list "2222" "RI-DWA_AFSCHEIDER_OLIE" 20 0.18 "CONTINUOUS" "2221" "G")
  (list "2272" "RI-DWA_RIOOLPUT_SLIBVANGER" 20 0.18 "CONTINUOUS" "2250" "G")
  (list "2237" "RI-DWA_PERCEELAANSLUITLEIDING_PVC" 20 0.18 "RI-DWA_AANSLUITLEIDING-SO" "2227" "G")
  (list "2232" "RI-DWA_PERCEELAANSLUITLEIDING_PE" 20 0.18 "RI-DWA_AANSLUITLEIDING-SO" "2227" "G")
  (list "3077" "RI-DWA_PERCEELAANSLUITLEIDING_PP" 20 0.18 "RI-DWA_AANSLUITLEIDING-SO" "2227" "G")
  (list "2228" "RI-DWA_PERCEELAANSLUITLEIDING_GRES" 20 0.18 "RI-DWA_AANSLUITLEIDING-SO" "2227" "G")
  (list "4021" "RI-DWA_TRANSPORTLEIDING-VOLZANDEN" 20 0.18 "RI-VOLZANDEN-SO" "2286" "G")
  (list "2311" "RI-DWA_TRANSPORTLEIDING_GRES" 20 0.18 "RI-DWA-SO" "2286" "G")
  (list "2287" "RI-DWA_TRANSPORTLEIDING_BETON" 20 0.18 "RI-DWA-SO" "2286" "G")
  (list "2332" "RI-DWA_TRANSPORTLEIDING_PVC" 20 0.18 "RI-DWA-SO" "2286" "G")
  (list "2322" "RI-DWA_TRANSPORTLEIDING_PE" 20 0.18 "RI-DWA-SO" "2286" "G")
  (list "4020" "RI-DWA_TRANSPORTLEIDING-VOLSCHUIMEN" 20 0.18 "RI-VOLSCHUIMEN-SO" "2286" "G")
  (list "4018" "RI-DWA_TRANSPORTLEIDING-OPHOOGTEBRENGEN" 20 0.18 "RI-OPHOOGTEBRENGEN-SO" "2286" "G")
  (list "4019" "RI-DWA_TRANSPORTLEIDING-LINING" 20 0.18 "RI-LINING-SO" "2286" "G")
  (list "4023" "RI-DWA_LOZELEIDING_VOLGESCHUIMD" 20 0.18 "RI-VOLSCHUIMEN-SO" "2340" "G")
  (list "4024" "RI-DWA_LOZELEIDING_VOLGEZAND" 20 0.18 "RI-VOLZANDEN-SO" "2340" "G")
  (list "4022" "RI-DWA_LOZELEIDING_UITLEGGER" 20 0.18 "RI-UITLEGGER-SO" "2340" "G")
  (list "2209" "RI-VACUUMLEIDING_HULPSTUK_INLAAT" 10 0.18 "CONTINUOUS" "2208" "G")
  (list "2210" "RI-VACUUMLEIDING_HULPSTUK_ONTSTOPPINGSSTUK" 10 0.18 "CONTINUOUS" "2208" "G")
  (list "2215" "RI-VACUUMLEIDING_RIOOLPUT_INSPECTIEPUT" 10 0.18 "CONTINUOUS" "2214" "G")
  (list "2207" "RI-VACUUMLEIDING_GEMAAL_BESTURINGSKAST" 10 0.18 "CONTINUOUS" "2206" "G")
  (list "2067" "RI-PERSLEIDING_GEMAAL_BESTURINGSKAST" 210 0.18 "CONTINUOUS" "2066" "G")
  (list "2075" "RI-PERSLEIDING_RIOOLPUT_INSPECTIEPUT" 210 0.18 "CONTINUOUS" "2074" "G")
  (list "4079" "RI-PERSLEIDING_LOZELEIDING_VOLGESCHUIMD" 210 0.18 "RI-VOLSCHUIMEN-SO" "4077" "G")
  (list "4080" "RI-PERSLEIDING_LOZELEIDING_VOLGEZAND" 210 0.18 "RI-VOLZANDEN-SO" "4077" "G")
  (list "4078" "RI-PERSLEIDING_LOZELEIDING_UITLEGGER" 210 0.18 "RI-UITLEGGER-SO" "4077" "G")
  (list "2070" "RI-PERSLEIDING_HULPSTUK_ONTSTOPPINGSSTUK" 210 0.18 "CONTINUOUS" "2068" "G")
  (list "2069" "RI-PERSLEIDING_HULPSTUK_INLAAT" 210 0.18 "CONTINUOUS" "2068" "G")
  (list "4045" "RI-GWA_LOZELEIDING_UITLEGGER" 30 0.18 "RI-UITLEGGER-SO" "1784" "G")
  (list "3692" "RI-GWA_LOZELEIDING_VOLGEZAND" 30 0.18 "RI-VOLZANDEN-SO" "1784" "G")
  (list "3691" "RI-GWA_LOZELEIDING_VOLGESCHUIMD" 30 0.18 "RI-VOLSCHUIMEN-SO" "1784" "G")
  (list "1776" "RI-GWA_TRANSPORTLEIDING_PVC" 30 0.18 "RI-GWA-SO" "1731" "G")
  (list "1756" "RI-GWA_TRANSPORTLEIDING_GRES" 30 0.18 "RI-GWA-SO" "1731" "G")
  (list "1732" "RI-GWA_TRANSPORTLEIDING_BETON" 30 0.18 "RI-GWA-SO" "1731" "G")
  (list "1767" "RI-GWA_TRANSPORTLEIDING_PE" 30 0.18 "RI-GWA-SO" "1731" "G")
  (list "3642" "RI-GWA_RIOOLLEIDING_GRES" 30 0.18 "RI-GWA-SO" "3613" "G")
  (list "3616" "RI-GWA_RIOOLLEIDING-VOLSCHUIMEN" 30 0.18 "RI-VOLSCHUIMEN-SO" "3613" "G")
  (list "3618" "RI-GWA_RIOOLLEIDING_BETON" 30 0.18 "RI-GWA-SO" "3613" "G")
  (list "3662" "RI-GWA_RIOOLLEIDING_PVC" 30 0.18 "RI-GWA-SO" "3613" "G")
  (list "4046" "RI-GWA_RIOOLLEIDING_STUWLEIDING" 30 0.18 "RI-GWA-SO" "3613" "G")
  (list "3653" "RI-GWA_RIOOLLEIDING_PE" 30 0.18 "RI-GWA-SO" "3613" "G")
  (list "3615" "RI-GWA_RIOOLLEIDING-LINING" 30 0.18 "RI-LINING-SO" "3613" "G")
  (list "3614" "RI-GWA_RIOOLLEIDING-OPHOOGTEBRENGEN" 30 0.18 "RI-OPHOOGTEBRENGEN-SO" "3613" "G")
  (list "3617" "RI-GWA_RIOOLLEIDING-VOLZANDEN" 30 0.18 "RI-VOLZANDEN-SO" "3613" "G")
  (list "4047" "RI-GWA_RIOOLLEIDING_ZINKER" 30 0.18 "RI-GWA-SO" "3613" "G")
  (list "3612" "RI-GWA_LOZINGSPUNT_OPPERVLAKTEWATER" 30 0.18 "CONTINUOUS" "1699" "G")
  (list "3611" "RI-GWA_LOZINGSPUNT_BODEM" 30 0.18 "CONTINUOUS" "1699" "G")
  (list "1668" "RI-GWA_PERCEELAANSLUITLEIDING_GRES" 30 0.18 "RI-GWA_AANSLUITLEIDING-SO" "1667" "G")
  (list "1672" "RI-GWA_PERCEELAANSLUITLEIDING_PE" 30 0.18 "RI-GWA_AANSLUITLEIDING-SO" "1667" "G")
  (list "1677" "RI-GWA_PERCEELAANSLUITLEIDING_PVC" 30 0.18 "RI-GWA_AANSLUITLEIDING-SO" "1667" "G")
  (list "1691" "RI-GWA_KOLKAANSLUITLEIDING_PE" 30 0.18 "RI-GWA_AANSLUITLEIDING-SO" "1690" "G")
  (list "1695" "RI-GWA_KOLKAANSLUITLEIDING_PVC" 30 0.18 "RI-GWA_AANSLUITLEIDING-SO" "1690" "G")
  (list "1658" "RI-DRAINAGE_PUT_FILTERPUT" 90 0.18 "CONTINUOUS" "1656" "G")
  (list "3592" "RI-DRAINAGE_HULPSTUK_STANDPIJP" 90 0.18 "CONTINUOUS" "1653" "G")
  (list "1639" "RI-DRAINAGE_DRAIN_PP" 90 0.18 "RI-DRAINAGE-SO" "1638" "G")
  (list "1646" "RI-DRAINAGE_DRAIN_PVC" 90 0.18 "RI-DRAINAGE-SO" "1638" "G")
  (list "3580" "RI-DRAINAGE_DRAIN-DOORSPOELEN" 90 0.18 "RI-DRAINAGE-SO" "1638" "G")
  (list "3579" "RI-DRAINAGE_DRAIN-OPHOOGTEBRENGEN" 90 0.18 "RI-OPHOOGTEBRENGEN-SO" "1638" "G")
  (list "3498" "RI-DRAINAGE_LOZELEIDING_UITLEGGER" 90 0.18 "CONTINUOUS" "3598" "G")
  (list "4066" "RI-OVERIG_DUIKER_LOZELEIDING_VOLGESCHUIMD" 10 0.18 "RI-VOLSCHUIMEN-SO" "4065" "G")
  (list "4067" "RI-OVERIG_DUIKER_LOZELEIDING_VOLGEZAND" 10 0.18 "RI-VOLZANDEN-SO" "4065" "G")
  (list "1852" "RI-HWA_RIOOLPUT_STUWPUT_BETON" 150 0.18 "CONTINUOUS" "1851" "G")
  (list "1853" "RI-HWA_RIOOLPUT_STUWPUT_PE" 150 0.18 "CONTINUOUS" "1851" "G")
  (list "1836" "RI-HWA_RIOOLPUT_BLINDEPUT_PE" 150 0.18 "CONTINUOUS" "1834" "G")
  (list "1835" "RI-HWA_RIOOLPUT_BLINDEPUT_BETON" 150 0.18 "CONTINUOUS" "1834" "G")
  (list "1846" "RI-HWA_RIOOLPUT_OVERSTORTPUT_BETON" 150 0.18 "CONTINUOUS" "1845" "G")
  (list "1847" "RI-HWA_RIOOLPUT_OVERSTORTPUT_PE" 150 0.18 "CONTINUOUS" "1845" "G")
  (list "1850" "RI-HWA_RIOOLPUT_POMPPUT_PE" 150 0.18 "CONTINUOUS" "1848" "G")
  (list "1849" "RI-HWA_RIOOLPUT_POMPPUT_BETON" 150 0.18 "CONTINUOUS" "1848" "G")
  (list "1840" "RI-HWA_RIOOLPUT_INSPECTIEPUT_BETON" 150 0.18 "CONTINUOUS" "1839" "G")
  (list "1841" "RI-HWA_RIOOLPUT_INSPECTIEPUT_PE" 150 0.18 "CONTINUOUS" "1839" "G")
  (list "1856" "RI-HWA_RIOOLPUT_VALPUT_PE" 150 0.18 "CONTINUOUS" "1854" "G")
  (list "1855" "RI-HWA_RIOOLPUT_VALPUT_BETON" 150 0.18 "CONTINUOUS" "1854" "G")
  (list "1915" "RI-HWA_TRANSPORTLEIDING_GVK_300" 150 0.18 "RI-HWA-SO" "1896" "G")
  (list "1897" "RI-HWA_TRANSPORTLEIDING_GVK_1000" 150 0.18 "RI-HWA-SO" "1896" "G")
  (list "1902" "RI-HWA_TRANSPORTLEIDING_GVK_1500" 150 0.18 "RI-HWA-SO" "1896" "G")
  (list "1904" "RI-HWA_TRANSPORTLEIDING_GVK_1700" 150 0.18 "RI-HWA-SO" "1896" "G")
  (list "1914" "RI-HWA_TRANSPORTLEIDING_GVK_2900" 150 0.18 "RI-HWA-SO" "1896" "G")
  (list "1911" "RI-HWA_TRANSPORTLEIDING_GVK_2500" 150 0.18 "RI-HWA-SO" "1896" "G")
  (list "1916" "RI-HWA_TRANSPORTLEIDING_GVK_350" 150 0.18 "RI-HWA-SO" "1896" "G")
  (list "1912" "RI-HWA_TRANSPORTLEIDING_GVK_2600" 150 0.18 "RI-HWA-SO" "1896" "G")
  (list "1899" "RI-HWA_TRANSPORTLEIDING_GVK_1200" 150 0.18 "RI-HWA-SO" "1896" "G")
  (list "1906" "RI-HWA_TRANSPORTLEIDING_GVK_200" 150 0.18 "RI-HWA-SO" "1896" "G")
  (list "1907" "RI-HWA_TRANSPORTLEIDING_GVK_2000" 150 0.18 "RI-HWA-SO" "1896" "G")
  (list "1919" "RI-HWA_TRANSPORTLEIDING_GVK_600" 150 0.18 "RI-HWA-SO" "1896" "G")
  (list "1908" "RI-HWA_TRANSPORTLEIDING_GVK_2200" 150 0.18 "RI-HWA-SO" "1896" "G")
  (list "1920" "RI-HWA_TRANSPORTLEIDING_GVK_700" 150 0.18 "RI-HWA-SO" "1896" "G")
  (list "1910" "RI-HWA_TRANSPORTLEIDING_GVK_250" 150 0.18 "RI-HWA-SO" "1896" "G")
  (list "1901" "RI-HWA_TRANSPORTLEIDING_GVK_150" 150 0.18 "RI-HWA-SO" "1896" "G")
  (list "1913" "RI-HWA_TRANSPORTLEIDING_GVK_2700" 150 0.18 "RI-HWA-SO" "1896" "G")
  (list "1921" "RI-HWA_TRANSPORTLEIDING_GVK_800" 150 0.18 "RI-HWA-SO" "1896" "G")
  (list "1905" "RI-HWA_TRANSPORTLEIDING_GVK_1800" 150 0.18 "RI-HWA-SO" "1896" "G")
  (list "1900" "RI-HWA_TRANSPORTLEIDING_GVK_1400" 150 0.18 "RI-HWA-SO" "1896" "G")
  (list "1917" "RI-HWA_TRANSPORTLEIDING_GVK_400" 150 0.18 "RI-HWA-SO" "1896" "G")
  (list "1903" "RI-HWA_TRANSPORTLEIDING_GVK_1600" 150 0.18 "RI-HWA-SO" "1896" "G")
  (list "1918" "RI-HWA_TRANSPORTLEIDING_GVK_500" 150 0.18 "RI-HWA-SO" "1896" "G")
  (list "1922" "RI-HWA_TRANSPORTLEIDING_GVK_900" 150 0.18 "RI-HWA-SO" "1896" "G")
  (list "1909" "RI-HWA_TRANSPORTLEIDING_GVK_2400" 150 0.18 "RI-HWA-SO" "1896" "G")
  (list "1898" "RI-HWA_TRANSPORTLEIDING_GVK_1100" 150 0.18 "RI-HWA-SO" "1896" "G")
  (list "1935" "RI-HWA_TRANSPORTLEIDING_PVC_200" 150 0.18 "RI-HWA-SO" "1933" "G")
  (list "2935" "RI-HWA_TRANSPORTLEIDING_PVC_125" 150 0.18 "RI-HWA-SO" "1933" "G")
  (list "1939" "RI-HWA_TRANSPORTLEIDING_PVC_500" 150 0.18 "RI-HWA-SO" "1933" "G")
  (list "1938" "RI-HWA_TRANSPORTLEIDING_PVC_400" 150 0.18 "RI-HWA-SO" "1933" "G")
  (list "1934" "RI-HWA_TRANSPORTLEIDING_PVC_160" 150 0.18 "RI-HWA-SO" "1933" "G")
  (list "1940" "RI-HWA_TRANSPORTLEIDING_PVC_630" 150 0.18 "RI-HWA-SO" "1933" "G")
  (list "1937" "RI-HWA_TRANSPORTLEIDING_PVC_315" 150 0.18 "RI-HWA-SO" "1933" "G")
  (list "1936" "RI-HWA_TRANSPORTLEIDING_PVC_250" 150 0.18 "RI-HWA-SO" "1933" "G")
  (list "1889" "RI-HWA_TRANSPORTLEIDING_GRES_300" 150 0.18 "RI-HWA-SO" "1885" "G")
  (list "1888" "RI-HWA_TRANSPORTLEIDING_GRES_250" 150 0.18 "RI-HWA-SO" "1885" "G")
  (list "1891" "RI-HWA_TRANSPORTLEIDING_GRES_500" 150 0.18 "RI-HWA-SO" "1885" "G")
  (list "1886" "RI-HWA_TRANSPORTLEIDING_GRES_1000" 150 0.18 "RI-HWA-SO" "1885" "G")
  (list "1895" "RI-HWA_TRANSPORTLEIDING_GRES_900" 150 0.18 "RI-HWA-SO" "1885" "G")
  (list "1887" "RI-HWA_TRANSPORTLEIDING_GRES_200" 150 0.18 "RI-HWA-SO" "1885" "G")
  (list "1892" "RI-HWA_TRANSPORTLEIDING_GRES_600" 150 0.18 "RI-HWA-SO" "1885" "G")
  (list "1890" "RI-HWA_TRANSPORTLEIDING_GRES_400" 150 0.18 "RI-HWA-SO" "1885" "G")
  (list "1893" "RI-HWA_TRANSPORTLEIDING_GRES_700" 150 0.18 "RI-HWA-SO" "1885" "G")
  (list "1894" "RI-HWA_TRANSPORTLEIDING_GRES_800" 150 0.18 "RI-HWA-SO" "1885" "G")
  (list "1862" "RI-HWA_TRANSPORTLEIDING_BETON_1000" 150 0.18 "RI-HWA-SO" "1861" "G")
  (list "1868" "RI-HWA_TRANSPORTLEIDING_BETON_400" 150 0.18 "RI-HWA-SO" "1861" "G")
  (list "1867" "RI-HWA_TRANSPORTLEIDING_BETON_300" 150 0.18 "RI-HWA-SO" "1861" "G")
  (list "1871" "RI-HWA_TRANSPORTLEIDING_BETON_700" 150 0.18 "RI-HWA-SO" "1861" "G")
  (list "1865" "RI-HWA_TRANSPORTLEIDING_BETON_2000" 150 0.18 "RI-HWA-SO" "1861" "G")
  (list "1863" "RI-HWA_TRANSPORTLEIDING_BETON_1250" 150 0.18 "RI-HWA-SO" "1861" "G")
  (list "1874" "RI-HWA_TRANSPORTLEIDING_BETON_EI" 150 0.18 "RI-HWA-SO" "1861" "G")
  (list "1866" "RI-HWA_TRANSPORTLEIDING_BETON_250" 150 0.18 "RI-HWA-SO" "1861" "G")
  (list "1873" "RI-HWA_TRANSPORTLEIDING_BETON_900" 150 0.18 "RI-HWA-SO" "1861" "G")
  (list "1869" "RI-HWA_TRANSPORTLEIDING_BETON_500" 150 0.18 "RI-HWA-SO" "1861" "G")
  (list "1870" "RI-HWA_TRANSPORTLEIDING_BETON_600" 150 0.18 "RI-HWA-SO" "1861" "G")
  (list "1872" "RI-HWA_TRANSPORTLEIDING_BETON_800" 150 0.18 "RI-HWA-SO" "1861" "G")
  (list "1864" "RI-HWA_TRANSPORTLEIDING_BETON_1500" 150 0.18 "RI-HWA-SO" "1861" "G")
  (list "1927" "RI-HWA_TRANSPORTLEIDING_PE_355" 150 0.18 "RI-HWA-SO" "1923" "G")
  (list "1925" "RI-HWA_TRANSPORTLEIDING_PE_250" 150 0.18 "RI-HWA-SO" "1923" "G")
  (list "1924" "RI-HWA_TRANSPORTLEIDING_PE_160" 150 0.18 "RI-HWA-SO" "1923" "G")
  (list "1929" "RI-HWA_TRANSPORTLEIDING_PE_450" 150 0.18 "RI-HWA-SO" "1923" "G")
  (list "1930" "RI-HWA_TRANSPORTLEIDING_PE_500" 150 0.18 "RI-HWA-SO" "1923" "G")
  (list "1928" "RI-HWA_TRANSPORTLEIDING_PE_400" 150 0.18 "RI-HWA-SO" "1923" "G")
  (list "1926" "RI-HWA_TRANSPORTLEIDING_PE_315" 150 0.18 "RI-HWA-SO" "1923" "G")
  (list "1931" "RI-HWA_TRANSPORTLEIDING_PE_560" 150 0.18 "RI-HWA-SO" "1923" "G")
  (list "1932" "RI-HWA_TRANSPORTLEIDING_PE_630" 150 0.18 "RI-HWA-SO" "1923" "G")
  (list "1825" "RI-HWA_KOLKAANSLUITLEIDING_PVC_160" 150 0.18 "RI-HWA_AANSLUITLEIDING-SO" "1822" "G")
  (list "1823" "RI-HWA_KOLKAANSLUITLEIDING_PVC_110" 150 0.18 "RI-HWA_AANSLUITLEIDING-SO" "1822" "G")
  (list "1824" "RI-HWA_KOLKAANSLUITLEIDING_PVC_125" 150 0.18 "RI-HWA_AANSLUITLEIDING-SO" "1822" "G")
  (list "1820" "RI-HWA_KOLKAANSLUITLEIDING_PE_125" 150 0.18 "RI-HWA_AANSLUITLEIDING-SO" "1818" "G")
  (list "1821" "RI-HWA_KOLKAANSLUITLEIDING_PE_160" 150 0.18 "RI-HWA_AANSLUITLEIDING-SO" "1818" "G")
  (list "1819" "RI-HWA_KOLKAANSLUITLEIDING_PE_110" 150 0.18 "RI-HWA_AANSLUITLEIDING-SO" "1818" "G")
  (list "1806" "RI-HWA_PERCEELAANSLUITLEIDING_PVC_110" 150 0.18 "RI-HWA_AANSLUITLEIDING-SO" "1805" "G")
  (list "1807" "RI-HWA_PERCEELAANSLUITLEIDING_PVC_125" 150 0.18 "RI-HWA_AANSLUITLEIDING-SO" "1805" "G")
  (list "1808" "RI-HWA_PERCEELAANSLUITLEIDING_PVC_160" 150 0.18 "RI-HWA_AANSLUITLEIDING-SO" "1805" "G")
  (list "1798" "RI-HWA_PERCEELAANSLUITLEIDING_GRES_125" 150 0.18 "RI-HWA_AANSLUITLEIDING-SO" "1796" "G")
  (list "1797" "RI-HWA_PERCEELAANSLUITLEIDING_GRES_100" 150 0.18 "RI-HWA_AANSLUITLEIDING-SO" "1796" "G")
  (list "1799" "RI-HWA_PERCEELAANSLUITLEIDING_GRES_150" 150 0.18 "RI-HWA_AANSLUITLEIDING-SO" "1796" "G")
  (list "3076" "RI-HWA_PERCEELAANSLUITLEIDING_PP_160" 150 0.18 "RI-HWA_AANSLUITLEIDING-SO" "3074" "G")
  (list "3075" "RI-HWA_PERCEELAANSLUITLEIDING_PP_125" 150 0.18 "RI-HWA_AANSLUITLEIDING-SO" "3074" "G")
  (list "1804" "RI-HWA_PERCEELAANSLUITLEIDING_PE_90" 150 0.18 "RI-HWA_AANSLUITLEIDING-SO" "1800" "G")
  (list "1803" "RI-HWA_PERCEELAANSLUITLEIDING_PE_75" 150 0.18 "RI-HWA_AANSLUITLEIDING-SO" "1800" "G")
  (list "1801" "RI-HWA_PERCEELAANSLUITLEIDING_PE_110" 150 0.18 "RI-HWA_AANSLUITLEIDING-SO" "1800" "G")
  (list "1802" "RI-HWA_PERCEELAANSLUITLEIDING_PE_63" 150 0.18 "RI-HWA_AANSLUITLEIDING-SO" "1800" "G")
  (list "1843" "RI-HWA_AANSLUITPUT_ONTSTOPPINGSPUT_BETON" 150 0.18 "CONTINUOUS" "1842" "G")
  (list "1844" "RI-HWA_AANSLUITPUT_ONTSTOPPINGSPUT_PE" 150 0.18 "CONTINUOUS" "1842" "G")
  (list "3696" "RI-HWA_GOOT_VERHOLENGOOT_ZANDVANGER" 150 0.18 "CONTINUOUS" "3695" "G")
  (list "3780" "RI-HWA_RIOOLLEIDING_PE_500" 150 0.18 "RI-HWA-SO" "3773" "G")
  (list "3778" "RI-HWA_RIOOLLEIDING_PE_400" 150 0.18 "RI-HWA-SO" "3773" "G")
  (list "3775" "RI-HWA_RIOOLLEIDING_PE_250" 150 0.18 "RI-HWA-SO" "3773" "G")
  (list "3776" "RI-HWA_RIOOLLEIDING_PE_315" 150 0.18 "RI-HWA-SO" "3773" "G")
  (list "3774" "RI-HWA_RIOOLLEIDING_PE_160" 150 0.18 "RI-HWA-SO" "3773" "G")
  (list "3777" "RI-HWA_RIOOLLEIDING_PE_355" 150 0.18 "RI-HWA-SO" "3773" "G")
  (list "3779" "RI-HWA_RIOOLLEIDING_PE_450" 150 0.18 "RI-HWA-SO" "3773" "G")
  (list "3782" "RI-HWA_RIOOLLEIDING_PE_630" 150 0.18 "RI-HWA-SO" "3773" "G")
  (list "3781" "RI-HWA_RIOOLLEIDING_PE_560" 150 0.18 "RI-HWA-SO" "3773" "G")
  (list "3747" "RI-HWA_RIOOLLEIDING_GVK_1000" 150 0.18 "RI-HWA-SO" "3746" "G")
  (list "3753" "RI-HWA_RIOOLLEIDING_GVK_1600" 150 0.18 "RI-HWA-SO" "3746" "G")
  (list "3767" "RI-HWA_RIOOLLEIDING_GVK_400" 150 0.18 "RI-HWA-SO" "3746" "G")
  (list "3760" "RI-HWA_RIOOLLEIDING_GVK_250" 150 0.18 "RI-HWA-SO" "3746" "G")
  (list "3765" "RI-HWA_RIOOLLEIDING_GVK_300" 150 0.18 "RI-HWA-SO" "3746" "G")
  (list "3757" "RI-HWA_RIOOLLEIDING_GVK_2000" 150 0.18 "RI-HWA-SO" "3746" "G")
  (list "3762" "RI-HWA_RIOOLLEIDING_GVK_2600" 150 0.18 "RI-HWA-SO" "3746" "G")
  (list "3758" "RI-HWA_RIOOLLEIDING_GVK_2200" 150 0.18 "RI-HWA-SO" "3746" "G")
  (list "3766" "RI-HWA_RIOOLLEIDING_GVK_350" 150 0.18 "RI-HWA-SO" "3746" "G")
  (list "3751" "RI-HWA_RIOOLLEIDING_GVK_150" 150 0.18 "RI-HWA-SO" "3746" "G")
  (list "3749" "RI-HWA_RIOOLLEIDING_GVK_1200" 150 0.18 "RI-HWA-SO" "3746" "G")
  (list "3768" "RI-HWA_RIOOLLEIDING_GVK_500" 150 0.18 "RI-HWA-SO" "3746" "G")
  (list "3770" "RI-HWA_RIOOLLEIDING_GVK_700" 150 0.18 "RI-HWA-SO" "3746" "G")
  (list "3759" "RI-HWA_RIOOLLEIDING_GVK_2400" 150 0.18 "RI-HWA-SO" "3746" "G")
  (list "3756" "RI-HWA_RIOOLLEIDING_GVK_200" 150 0.18 "RI-HWA-SO" "3746" "G")
  (list "3748" "RI-HWA_RIOOLLEIDING_GVK_1100" 150 0.18 "RI-HWA-SO" "3746" "G")
  (list "3761" "RI-HWA_RIOOLLEIDING_GVK_2500" 150 0.18 "RI-HWA-SO" "3746" "G")
  (list "3763" "RI-HWA_RIOOLLEIDING_GVK_2700" 150 0.18 "RI-HWA-SO" "3746" "G")
  (list "3755" "RI-HWA_RIOOLLEIDING_GVK_1800" 150 0.18 "RI-HWA-SO" "3746" "G")
  (list "3771" "RI-HWA_RIOOLLEIDING_GVK_800" 150 0.18 "RI-HWA-SO" "3746" "G")
  (list "3752" "RI-HWA_RIOOLLEIDING_GVK_1500" 150 0.18 "RI-HWA-SO" "3746" "G")
  (list "3772" "RI-HWA_RIOOLLEIDING_GVK_900" 150 0.18 "RI-HWA-SO" "3746" "G")
  (list "3764" "RI-HWA_RIOOLLEIDING_GVK_2900" 150 0.18 "RI-HWA-SO" "3746" "G")
  (list "3754" "RI-HWA_RIOOLLEIDING_GVK_1700" 150 0.18 "RI-HWA-SO" "3746" "G")
  (list "3769" "RI-HWA_RIOOLLEIDING_GVK_600" 150 0.18 "RI-HWA-SO" "3746" "G")
  (list "3750" "RI-HWA_RIOOLLEIDING_GVK_1400" 150 0.18 "RI-HWA-SO" "3746" "G")
  (list "3791" "RI-HWA_RIOOLLEIDING_PVC_630" 150 0.18 "RI-HWA-SO" "3783" "G")
  (list "3790" "RI-HWA_RIOOLLEIDING_PVC_500" 150 0.18 "RI-HWA-SO" "3783" "G")
  (list "3789" "RI-HWA_RIOOLLEIDING_PVC_400" 150 0.18 "RI-HWA-SO" "3783" "G")
  (list "3785" "RI-HWA_RIOOLLEIDING_PVC_160" 150 0.18 "RI-HWA-SO" "3783" "G")
  (list "3788" "RI-HWA_RIOOLLEIDING_PVC_315" 150 0.18 "RI-HWA-SO" "3783" "G")
  (list "3786" "RI-HWA_RIOOLLEIDING_PVC_200" 150 0.18 "RI-HWA-SO" "3783" "G")
  (list "3784" "RI-HWA_RIOOLLEIDING_PVC_125" 150 0.18 "RI-HWA-SO" "3783" "G")
  (list "3787" "RI-HWA_RIOOLLEIDING_PVC_250" 150 0.18 "RI-HWA-SO" "3783" "G")
  (list "3724" "RI-HWA_RIOOLLEIDING_BETON_EI" 150 0.18 "RI-HWA-SO" "3711" "G")
  (list "3717" "RI-HWA_RIOOLLEIDING_BETON_300" 150 0.18 "RI-HWA-SO" "3711" "G")
  (list "3721" "RI-HWA_RIOOLLEIDING_BETON_700" 150 0.18 "RI-HWA-SO" "3711" "G")
  (list "3720" "RI-HWA_RIOOLLEIDING_BETON_600" 150 0.18 "RI-HWA-SO" "3711" "G")
  (list "3714" "RI-HWA_RIOOLLEIDING_BETON_1500" 150 0.18 "RI-HWA-SO" "3711" "G")
  (list "3715" "RI-HWA_RIOOLLEIDING_BETON_2000" 150 0.18 "RI-HWA-SO" "3711" "G")
  (list "3723" "RI-HWA_RIOOLLEIDING_BETON_900" 150 0.18 "RI-HWA-SO" "3711" "G")
  (list "3719" "RI-HWA_RIOOLLEIDING_BETON_500" 150 0.18 "RI-HWA-SO" "3711" "G")
  (list "3712" "RI-HWA_RIOOLLEIDING_BETON_1000" 150 0.18 "RI-HWA-SO" "3711" "G")
  (list "3722" "RI-HWA_RIOOLLEIDING_BETON_800" 150 0.18 "RI-HWA-SO" "3711" "G")
  (list "3718" "RI-HWA_RIOOLLEIDING_BETON_400" 150 0.18 "RI-HWA-SO" "3711" "G")
  (list "3713" "RI-HWA_RIOOLLEIDING_BETON_1250" 150 0.18 "RI-HWA-SO" "3711" "G")
  (list "3716" "RI-HWA_RIOOLLEIDING_BETON_250" 150 0.18 "RI-HWA-SO" "3711" "G")
  (list "3742" "RI-HWA_RIOOLLEIDING_GRES_600" 150 0.18 "RI-HWA-SO" "3735" "G")
  (list "3744" "RI-HWA_RIOOLLEIDING_GRES_800" 150 0.18 "RI-HWA-SO" "3735" "G")
  (list "3736" "RI-HWA_RIOOLLEIDING_GRES_1000" 150 0.18 "RI-HWA-SO" "3735" "G")
  (list "3741" "RI-HWA_RIOOLLEIDING_GRES_500" 150 0.18 "RI-HWA-SO" "3735" "G")
  (list "3738" "RI-HWA_RIOOLLEIDING_GRES_250" 150 0.18 "RI-HWA-SO" "3735" "G")
  (list "3740" "RI-HWA_RIOOLLEIDING_GRES_400" 150 0.18 "RI-HWA-SO" "3735" "G")
  (list "3745" "RI-HWA_RIOOLLEIDING_GRES_900" 150 0.18 "RI-HWA-SO" "3735" "G")
  (list "3743" "RI-HWA_RIOOLLEIDING_GRES_700" 150 0.18 "RI-HWA-SO" "3735" "G")
  (list "3739" "RI-HWA_RIOOLLEIDING_GRES_300" 150 0.18 "RI-HWA-SO" "3735" "G")
  (list "3737" "RI-HWA_RIOOLLEIDING_GRES_200" 150 0.18 "RI-HWA-SO" "3735" "G")
  (list "3828" "RI-ITR_RESERVOIR_INFILTRATIERESERVOIR_INFILTRATIEBASSIN" 50 0.18 "CONTINUOUS" "3826" "G")
  (list "3832" "RI-ITR_RESERVOIR_INFILTRATIERESERVOIR_ZANDKOFFER" 50 0.18 "CONTINUOUS" "3826" "G")
  (list "3830" "RI-ITR_RESERVOIR_INFILTRATIERESERVOIR_WADI" 50 0.18 "CONTINUOUS" "3826" "G")
  (list "3831" "RI-ITR_RESERVOIR_INFILTRATIERESERVOIR_STEENWOLKOFFER" 50 0.18 "CONTINUOUS" "3826" "G")
  (list "3829" "RI-ITR_RESERVOIR_INFILTRATIERESERVOIR_INFILTRATIEGREPPEL" 50 0.18 "CONTINUOUS" "3826" "G")
  (list "3827" "RI-ITR_RESERVOIR_INFILTRATIERESERVOIR_GRINDKOFFER" 50 0.18 "CONTINUOUS" "3826" "G")
  (list "3835" "RI-ITR_RESERVOIR_ZUIVERINGSRESERVOIR_IBA" 50 0.18 "CONTINUOUS" "3834" "G")
  (list "1969" "RI-ITR_KOLKAANSLUITLEIDING_PE_125" 50 0.18 "RI-ITR_AANSLUITLEIDING-SO" "1967" "G")
  (list "1970" "RI-ITR_KOLKAANSLUITLEIDING_PE_160" 50 0.18 "RI-ITR_AANSLUITLEIDING-SO" "1967" "G")
  (list "1968" "RI-ITR_KOLKAANSLUITLEIDING_PE_110" 50 0.18 "RI-ITR_AANSLUITLEIDING-SO" "1967" "G")
  (list "1972" "RI-ITR_KOLKAANSLUITLEIDING_PVC_110" 50 0.18 "RI-ITR_AANSLUITLEIDING-SO" "1971" "G")
  (list "1974" "RI-ITR_KOLKAANSLUITLEIDING_PVC_160" 50 0.18 "RI-ITR_AANSLUITLEIDING-SO" "1971" "G")
  (list "1973" "RI-ITR_KOLKAANSLUITLEIDING_PVC_125" 50 0.18 "RI-ITR_AANSLUITLEIDING-SO" "1971" "G")
  (list "2013" "RI-ITR_RIOOLPUT_VALPUT_PE" 50 0.18 "CONTINUOUS" "2011" "G")
  (list "2012" "RI-ITR_RIOOLPUT_VALPUT_BETON" 50 0.18 "CONTINUOUS" "2011" "G")
  (list "1992" "RI-ITR_RIOOLPUT_BLINDEPUT_BETON" 50 0.18 "CONTINUOUS" "1991" "G")
  (list "1993" "RI-ITR_RIOOLPUT_BLINDEPUT_PE" 50 0.18 "CONTINUOUS" "1991" "G")
  (list "2007" "RI-ITR_RIOOLPUT_POMPPUT_PE" 50 0.18 "CONTINUOUS" "2005" "G")
  (list "2006" "RI-ITR_RIOOLPUT_POMPPUT_BETON" 50 0.18 "CONTINUOUS" "2005" "G")
  (list "2009" "RI-ITR_RIOOLPUT_STUWPUT_BETON" 50 0.18 "CONTINUOUS" "2008" "G")
  (list "2010" "RI-ITR_RIOOLPUT_STUWPUT_PE" 50 0.18 "CONTINUOUS" "2008" "G")
  (list "1998" "RI-ITR_RIOOLPUT_INSPECTIEPUT_PE" 50 0.18 "CONTINUOUS" "1996" "G")
  (list "1997" "RI-ITR_RIOOLPUT_INSPECTIEPUT_BETON" 50 0.18 "CONTINUOUS" "1996" "G")
  (list "2003" "RI-ITR_RIOOLPUT_OVERSTORTPUT_BETON" 50 0.18 "CONTINUOUS" "2002" "G")
  (list "2004" "RI-ITR_RIOOLPUT_OVERSTORTPUT_PE" 50 0.18 "CONTINUOUS" "2002" "G")
  (list "1995" "RI-ITR_RIOOLPUT_HONDEHOKPUT_BETON" 50 0.18 "CONTINUOUS" "1994" "G")
  (list "2001" "RI-ITR_AANSLUITPUT_ONTSTOPPINGSPUT_PE" 50 0.18 "CONTINUOUS" "1999" "G")
  (list "2000" "RI-ITR_AANSLUITPUT_ONTSTOPPINGSPUT_BETON" 50 0.18 "CONTINUOUS" "1999" "G")
  (list "2037" "RI-ITR_RIOOLLEIDING_PE_450" 50 0.18 "RI-ITR-SO" "2031" "G")
  (list "2032" "RI-ITR_RIOOLLEIDING_PE_160" 50 0.18 "RI-ITR-SO" "2031" "G")
  (list "2034" "RI-ITR_RIOOLLEIDING_PE_315" 50 0.18 "RI-ITR-SO" "2031" "G")
  (list "2040" "RI-ITR_RIOOLLEIDING_PE_630" 50 0.18 "RI-ITR-SO" "2031" "G")
  (list "2036" "RI-ITR_RIOOLLEIDING_PE_400" 50 0.18 "RI-ITR-SO" "2031" "G")
  (list "2035" "RI-ITR_RIOOLLEIDING_PE_355" 50 0.18 "RI-ITR-SO" "2031" "G")
  (list "2033" "RI-ITR_RIOOLLEIDING_PE_250" 50 0.18 "RI-ITR-SO" "2031" "G")
  (list "2039" "RI-ITR_RIOOLLEIDING_PE_560" 50 0.18 "RI-ITR-SO" "2031" "G")
  (list "2038" "RI-ITR_RIOOLLEIDING_PE_500" 50 0.18 "RI-ITR-SO" "2031" "G")
  (list "2028" "RI-ITR_RIOOLLEIDING_BETON_700" 50 0.18 "RI-ITR-SO" "2018" "G")
  (list "2030" "RI-ITR_RIOOLLEIDING_BETON_900" 50 0.18 "RI-ITR-SO" "2018" "G")
  (list "2024" "RI-ITR_RIOOLLEIDING_BETON_300" 50 0.18 "RI-ITR-SO" "2018" "G")
  (list "2022" "RI-ITR_RIOOLLEIDING_BETON_2000" 50 0.18 "RI-ITR-SO" "2018" "G")
  (list "2021" "RI-ITR_RIOOLLEIDING_BETON_1500" 50 0.18 "RI-ITR-SO" "2018" "G")
  (list "2027" "RI-ITR_RIOOLLEIDING_BETON_600" 50 0.18 "RI-ITR-SO" "2018" "G")
  (list "2025" "RI-ITR_RIOOLLEIDING_BETON_400" 50 0.18 "RI-ITR-SO" "2018" "G")
  (list "2019" "RI-ITR_RIOOLLEIDING_BETON_1000" 50 0.18 "RI-ITR-SO" "2018" "G")
  (list "2026" "RI-ITR_RIOOLLEIDING_BETON_500" 50 0.18 "RI-ITR-SO" "2018" "G")
  (list "2029" "RI-ITR_RIOOLLEIDING_BETON_800" 50 0.18 "RI-ITR-SO" "2018" "G")
  (list "2023" "RI-ITR_RIOOLLEIDING_BETON_250" 50 0.18 "RI-ITR-SO" "2018" "G")
  (list "2020" "RI-ITR_RIOOLLEIDING_BETON_1250" 50 0.18 "RI-ITR-SO" "2018" "G")
  (list "2048" "RI-ITR_RIOOLLEIDING_PVC_630" 50 0.18 "RI-ITR-SO" "2041" "G")
  (list "2045" "RI-ITR_RIOOLLEIDING_PVC_315" 50 0.18 "RI-ITR-SO" "2041" "G")
  (list "2046" "RI-ITR_RIOOLLEIDING_PVC_400" 50 0.18 "RI-ITR-SO" "2041" "G")
  (list "2047" "RI-ITR_RIOOLLEIDING_PVC_500" 50 0.18 "RI-ITR-SO" "2041" "G")
  (list "2043" "RI-ITR_RIOOLLEIDING_PVC_200" 50 0.18 "RI-ITR-SO" "2041" "G")
  (list "2044" "RI-ITR_RIOOLLEIDING_PVC_250" 50 0.18 "RI-ITR-SO" "2041" "G")
  (list "2042" "RI-ITR_RIOOLLEIDING_PVC_160" 50 0.18 "RI-ITR-SO" "2041" "G")
  (list "1957" "RI-ITR_PERCEELAANSLUITLEIDING_PVC_160" 50 0.18 "RI-ITR_AANSLUITLEIDING-SO" "1954" "G")
  (list "1956" "RI-ITR_PERCEELAANSLUITLEIDING_PVC_125" 50 0.18 "RI-ITR_AANSLUITLEIDING-SO" "1954" "G")
  (list "1955" "RI-ITR_PERCEELAANSLUITLEIDING_PVC_110" 50 0.18 "RI-ITR_AANSLUITLEIDING-SO" "1954" "G")
  (list "1950" "RI-ITR_PERCEELAANSLUITLEIDING_PE_110" 50 0.18 "RI-ITR_AANSLUITLEIDING-SO" "1949" "G")
  (list "1953" "RI-ITR_PERCEELAANSLUITLEIDING_PE_90" 50 0.18 "RI-ITR_AANSLUITLEIDING-SO" "1949" "G")
  (list "1951" "RI-ITR_PERCEELAANSLUITLEIDING_PE_63" 50 0.18 "RI-ITR_AANSLUITLEIDING-SO" "1949" "G")
  (list "1952" "RI-ITR_PERCEELAANSLUITLEIDING_PE_75" 50 0.18 "RI-ITR_AANSLUITLEIDING-SO" "1949" "G")
  (list "3978" "RI-DWA_RIOOLLEIDING_GRES_800" 20 0.18 "RI-DWA-SO" "3969" "G")
  (list "3970" "RI-DWA_RIOOLLEIDING_GRES_1000" 20 0.18 "RI-DWA-SO" "3969" "G")
  (list "3973" "RI-DWA_RIOOLLEIDING_GRES_300" 20 0.18 "RI-DWA-SO" "3969" "G")
  (list "3972" "RI-DWA_RIOOLLEIDING_GRES_250" 20 0.18 "RI-DWA-SO" "3969" "G")
  (list "3979" "RI-DWA_RIOOLLEIDING_GRES_900" 20 0.18 "RI-DWA-SO" "3969" "G")
  (list "3977" "RI-DWA_RIOOLLEIDING_GRES_700" 20 0.18 "RI-DWA-SO" "3969" "G")
  (list "3976" "RI-DWA_RIOOLLEIDING_GRES_600" 20 0.18 "RI-DWA-SO" "3969" "G")
  (list "3975" "RI-DWA_RIOOLLEIDING_GRES_500" 20 0.18 "RI-DWA-SO" "3969" "G")
  (list "3971" "RI-DWA_RIOOLLEIDING_GRES_200" 20 0.18 "RI-DWA-SO" "3969" "G")
  (list "3974" "RI-DWA_RIOOLLEIDING_GRES_400" 20 0.18 "RI-DWA-SO" "3969" "G")
  (list "3986" "RI-DWA_RIOOLLEIDING_PE_450" 20 0.18 "RI-DWA-SO" "3980" "G")
  (list "3984" "RI-DWA_RIOOLLEIDING_PE_355" 20 0.18 "RI-DWA-SO" "3980" "G")
  (list "3987" "RI-DWA_RIOOLLEIDING_PE_500" 20 0.18 "RI-DWA-SO" "3980" "G")
  (list "3988" "RI-DWA_RIOOLLEIDING_PE_560" 20 0.18 "RI-DWA-SO" "3980" "G")
  (list "3983" "RI-DWA_RIOOLLEIDING_PE_315" 20 0.18 "RI-DWA-SO" "3980" "G")
  (list "3982" "RI-DWA_RIOOLLEIDING_PE_250" 20 0.18 "RI-DWA-SO" "3980" "G")
  (list "3985" "RI-DWA_RIOOLLEIDING_PE_400" 20 0.18 "RI-DWA-SO" "3980" "G")
  (list "3981" "RI-DWA_RIOOLLEIDING_PE_160" 20 0.18 "RI-DWA-SO" "3980" "G")
  (list "3989" "RI-DWA_RIOOLLEIDING_PE_630" 20 0.18 "RI-DWA-SO" "3980" "G")
  (list "3994" "RI-DWA_RIOOLLEIDING_PVC_315" 20 0.18 "RI-DWA-SO" "3990" "G")
  (list "3997" "RI-DWA_RIOOLLEIDING_PVC_630" 20 0.18 "RI-DWA-SO" "3990" "G")
  (list "3992" "RI-DWA_RIOOLLEIDING_PVC_200" 20 0.18 "RI-DWA-SO" "3990" "G")
  (list "3993" "RI-DWA_RIOOLLEIDING_PVC_250" 20 0.18 "RI-DWA-SO" "3990" "G")
  (list "3991" "RI-DWA_RIOOLLEIDING_PVC_160" 20 0.18 "RI-DWA-SO" "3990" "G")
  (list "3995" "RI-DWA_RIOOLLEIDING_PVC_400" 20 0.18 "RI-DWA-SO" "3990" "G")
  (list "3996" "RI-DWA_RIOOLLEIDING_PVC_500" 20 0.18 "RI-DWA-SO" "3990" "G")
  (list "3956" "RI-DWA_RIOOLLEIDING_BETON_800" 20 0.18 "RI-DWA-SO" "3945" "G")
  (list "3958" "RI-DWA_RIOOLLEIDING_BETON_EI" 20 0.18 "RI-DWA-SO" "3945" "G")
  (list "3953" "RI-DWA_RIOOLLEIDING_BETON_500" 20 0.18 "RI-DWA-SO" "3945" "G")
  (list "3955" "RI-DWA_RIOOLLEIDING_BETON_700" 20 0.18 "RI-DWA-SO" "3945" "G")
  (list "3949" "RI-DWA_RIOOLLEIDING_BETON_2000" 20 0.18 "RI-DWA-SO" "3945" "G")
  (list "3947" "RI-DWA_RIOOLLEIDING_BETON_1250" 20 0.18 "RI-DWA-SO" "3945" "G")
  (list "3951" "RI-DWA_RIOOLLEIDING_BETON_300" 20 0.18 "RI-DWA-SO" "3945" "G")
  (list "3948" "RI-DWA_RIOOLLEIDING_BETON_1500" 20 0.18 "RI-DWA-SO" "3945" "G")
  (list "3954" "RI-DWA_RIOOLLEIDING_BETON_600" 20 0.18 "RI-DWA-SO" "3945" "G")
  (list "3952" "RI-DWA_RIOOLLEIDING_BETON_400" 20 0.18 "RI-DWA-SO" "3945" "G")
  (list "3957" "RI-DWA_RIOOLLEIDING_BETON_900" 20 0.18 "RI-DWA-SO" "3945" "G")
  (list "3950" "RI-DWA_RIOOLLEIDING_BETON_250" 20 0.18 "RI-DWA-SO" "3945" "G")
  (list "3946" "RI-DWA_RIOOLLEIDING_BETON_1000" 20 0.18 "RI-DWA-SO" "3945" "G")
  (list "2253" "RI-DWA_RIOOLPUT_BLINDEPUT_BETON" 20 0.18 "CONTINUOUS" "2252" "G")
  (list "2254" "RI-DWA_RIOOLPUT_BLINDEPUT_PE" 20 0.18 "CONTINUOUS" "2252" "G")
  (list "2267" "RI-DWA_RIOOLPUT_OVERSTORTPUT_BETON" 20 0.18 "CONTINUOUS" "2266" "G")
  (list "2268" "RI-DWA_RIOOLPUT_OVERSTORTPUT_PE" 20 0.18 "CONTINUOUS" "2266" "G")
  (list "2278" "RI-DWA_RIOOLPUT_VALPUT_BETON" 20 0.18 "CONTINUOUS" "2277" "G")
  (list "2279" "RI-DWA_RIOOLPUT_VALPUT_PE" 20 0.18 "CONTINUOUS" "2277" "G")
  (list "2273" "RI-DWA_RIOOLPUT_SLIBVANGER_BETON" 20 0.18 "CONTINUOUS" "2272" "G")
  (list "2261" "RI-DWA_RIOOLPUT_MONSTERNAMEPUT_BETON" 20 0.18 "CONTINUOUS" "2260" "G")
  (list "2262" "RI-DWA_RIOOLPUT_MONSTERNAMEPUT_PE" 20 0.18 "CONTINUOUS" "2260" "G")
  (list "2270" "RI-DWA_RIOOLPUT_POMPPUT_BETON" 20 0.18 "CONTINUOUS" "2269" "G")
  (list "2271" "RI-DWA_RIOOLPUT_POMPPUT_PE" 20 0.18 "CONTINUOUS" "2269" "G")
  (list "2258" "RI-DWA_RIOOLPUT_INSPECTIEPUT_BETON" 20 0.18 "CONTINUOUS" "2257" "G")
  (list "2259" "RI-DWA_RIOOLPUT_INSPECTIEPUT_PE" 20 0.18 "CONTINUOUS" "2257" "G")
  (list "2281" "RI-DWA_RIOOLPUT_ZANDVANGPUT_BETON" 20 0.18 "CONTINUOUS" "2280" "G")
  (list "2276" "RI-DWA_RIOOLPUT_STUWPUT_PE" 20 0.18 "CONTINUOUS" "2274" "G")
  (list "2275" "RI-DWA_RIOOLPUT_STUWPUT_BETON" 20 0.18 "CONTINUOUS" "2274" "G")
  (list "2239" "RI-DWA_PERCEELAANSLUITLEIDING_PVC_125" 20 0.18 "RI-DWA_AANSLUITLEIDING-SO" "2237" "G")
  (list "2238" "RI-DWA_PERCEELAANSLUITLEIDING_PVC_110" 20 0.18 "RI-DWA_AANSLUITLEIDING-SO" "2237" "G")
  (list "2240" "RI-DWA_PERCEELAANSLUITLEIDING_PVC_160" 20 0.18 "RI-DWA_AANSLUITLEIDING-SO" "2237" "G")
  (list "2233" "RI-DWA_PERCEELAANSLUITLEIDING_PE_110" 20 0.18 "RI-DWA_AANSLUITLEIDING-SO" "2232" "G")
  (list "2234" "RI-DWA_PERCEELAANSLUITLEIDING_PE_63" 20 0.18 "RI-DWA_AANSLUITLEIDING-SO" "2232" "G")
  (list "2235" "RI-DWA_PERCEELAANSLUITLEIDING_PE_75" 20 0.18 "RI-DWA_AANSLUITLEIDING-SO" "2232" "G")
  (list "2236" "RI-DWA_PERCEELAANSLUITLEIDING_PE_90" 20 0.18 "RI-DWA_AANSLUITLEIDING-SO" "2232" "G")
  (list "3079" "RI-DWA_PERCEELAANSLUITLEIDING_PP_160" 20 0.18 "RI-DWA_AANSLUITLEIDING-SO" "3077" "G")
  (list "3078" "RI-DWA_PERCEELAANSLUITLEIDING_PP_125" 20 0.18 "RI-DWA_AANSLUITLEIDING-SO" "3077" "G")
  (list "2230" "RI-DWA_PERCEELAANSLUITLEIDING_GRES_125" 20 0.18 "RI-DWA_AANSLUITLEIDING-SO" "2228" "G")
  (list "2229" "RI-DWA_PERCEELAANSLUITLEIDING_GRES_100" 20 0.18 "RI-DWA_AANSLUITLEIDING-SO" "2228" "G")
  (list "2231" "RI-DWA_PERCEELAANSLUITLEIDING_GRES_150" 20 0.18 "RI-DWA_AANSLUITLEIDING-SO" "2228" "G")
  (list "2317" "RI-DWA_TRANSPORTLEIDING_GRES_500" 20 0.18 "RI-DWA-SO" "2311" "G")
  (list "2314" "RI-DWA_TRANSPORTLEIDING_GRES_250" 20 0.18 "RI-DWA-SO" "2311" "G")
  (list "2315" "RI-DWA_TRANSPORTLEIDING_GRES_300" 20 0.18 "RI-DWA-SO" "2311" "G")
  (list "2320" "RI-DWA_TRANSPORTLEIDING_GRES_800" 20 0.18 "RI-DWA-SO" "2311" "G")
  (list "2316" "RI-DWA_TRANSPORTLEIDING_GRES_400" 20 0.18 "RI-DWA-SO" "2311" "G")
  (list "2319" "RI-DWA_TRANSPORTLEIDING_GRES_700" 20 0.18 "RI-DWA-SO" "2311" "G")
  (list "2312" "RI-DWA_TRANSPORTLEIDING_GRES_1000" 20 0.18 "RI-DWA-SO" "2311" "G")
  (list "2318" "RI-DWA_TRANSPORTLEIDING_GRES_600" 20 0.18 "RI-DWA-SO" "2311" "G")
  (list "2321" "RI-DWA_TRANSPORTLEIDING_GRES_900" 20 0.18 "RI-DWA-SO" "2311" "G")
  (list "2313" "RI-DWA_TRANSPORTLEIDING_GRES_200" 20 0.18 "RI-DWA-SO" "2311" "G")
  (list "2294" "RI-DWA_TRANSPORTLEIDING_BETON_400" 20 0.18 "RI-DWA-SO" "2287" "G")
  (list "2300" "RI-DWA_TRANSPORTLEIDING_BETON_EI" 20 0.18 "RI-DWA-SO" "2287" "G")
  (list "2290" "RI-DWA_TRANSPORTLEIDING_BETON_1500" 20 0.18 "RI-DWA-SO" "2287" "G")
  (list "2295" "RI-DWA_TRANSPORTLEIDING_BETON_500" 20 0.18 "RI-DWA-SO" "2287" "G")
  (list "2288" "RI-DWA_TRANSPORTLEIDING_BETON_1000" 20 0.18 "RI-DWA-SO" "2287" "G")
  (list "2292" "RI-DWA_TRANSPORTLEIDING_BETON_250" 20 0.18 "RI-DWA-SO" "2287" "G")
  (list "2299" "RI-DWA_TRANSPORTLEIDING_BETON_900" 20 0.18 "RI-DWA-SO" "2287" "G")
  (list "2293" "RI-DWA_TRANSPORTLEIDING_BETON_300" 20 0.18 "RI-DWA-SO" "2287" "G")
  (list "2297" "RI-DWA_TRANSPORTLEIDING_BETON_700" 20 0.18 "RI-DWA-SO" "2287" "G")
  (list "2296" "RI-DWA_TRANSPORTLEIDING_BETON_600" 20 0.18 "RI-DWA-SO" "2287" "G")
  (list "2298" "RI-DWA_TRANSPORTLEIDING_BETON_800" 20 0.18 "RI-DWA-SO" "2287" "G")
  (list "2289" "RI-DWA_TRANSPORTLEIDING_BETON_1250" 20 0.18 "RI-DWA-SO" "2287" "G")
  (list "2291" "RI-DWA_TRANSPORTLEIDING_BETON_2000" 20 0.18 "RI-DWA-SO" "2287" "G")
  (list "2336" "RI-DWA_TRANSPORTLEIDING_PVC_315" 20 0.18 "RI-DWA-SO" "2332" "G")
  (list "2335" "RI-DWA_TRANSPORTLEIDING_PVC_250" 20 0.18 "RI-DWA-SO" "2332" "G")
  (list "2334" "RI-DWA_TRANSPORTLEIDING_PVC_200" 20 0.18 "RI-DWA-SO" "2332" "G")
  (list "2338" "RI-DWA_TRANSPORTLEIDING_PVC_500" 20 0.18 "RI-DWA-SO" "2332" "G")
  (list "2337" "RI-DWA_TRANSPORTLEIDING_PVC_400" 20 0.18 "RI-DWA-SO" "2332" "G")
  (list "2339" "RI-DWA_TRANSPORTLEIDING_PVC_630" 20 0.18 "RI-DWA-SO" "2332" "G")
  (list "2333" "RI-DWA_TRANSPORTLEIDING_PVC_160" 20 0.18 "RI-DWA-SO" "2332" "G")
  (list "2327" "RI-DWA_TRANSPORTLEIDING_PE_400" 20 0.18 "RI-DWA-SO" "2322" "G")
  (list "2323" "RI-DWA_TRANSPORTLEIDING_PE_160" 20 0.18 "RI-DWA-SO" "2322" "G")
  (list "2326" "RI-DWA_TRANSPORTLEIDING_PE_355" 20 0.18 "RI-DWA-SO" "2322" "G")
  (list "2330" "RI-DWA_TRANSPORTLEIDING_PE_560" 20 0.18 "RI-DWA-SO" "2322" "G")
  (list "2325" "RI-DWA_TRANSPORTLEIDING_PE_315" 20 0.18 "RI-DWA-SO" "2322" "G")
  (list "2331" "RI-DWA_TRANSPORTLEIDING_PE_630" 20 0.18 "RI-DWA-SO" "2322" "G")
  (list "2328" "RI-DWA_TRANSPORTLEIDING_PE_450" 20 0.18 "RI-DWA-SO" "2322" "G")
  (list "2329" "RI-DWA_TRANSPORTLEIDING_PE_500" 20 0.18 "RI-DWA-SO" "2322" "G")
  (list "2324" "RI-DWA_TRANSPORTLEIDING_PE_250" 20 0.18 "RI-DWA-SO" "2322" "G")
  (list "2265" "RI-DWA_AANSLUITPUT_ONTSTOPPINGSPUT_PE" 20 0.18 "CONTINUOUS" "2263" "G")
  (list "2264" "RI-DWA_AANSLUITPUT_ONTSTOPPINGSPUT_BETON" 20 0.18 "CONTINUOUS" "2263" "G")
  (list "1718" "RI-GWA_RIOOLPUT_OVERSTORTPUT_PE" 30 0.18 "CONTINUOUS" "1716" "G")
  (list "1717" "RI-GWA_RIOOLPUT_OVERSTORTPUT_BETON" 30 0.18 "CONTINUOUS" "1716" "G")
  (list "1711" "RI-GWA_RIOOLPUT_INSPECTIEPUT_BETON" 30 0.18 "CONTINUOUS" "1710" "G")
  (list "1712" "RI-GWA_RIOOLPUT_INSPECTIEPUT_PE" 30 0.18 "CONTINUOUS" "1710" "G")
  (list "1720" "RI-GWA_RIOOLPUT_POMPPUT_BETON" 30 0.18 "CONTINUOUS" "1719" "G")
  (list "1721" "RI-GWA_RIOOLPUT_POMPPUT_PE" 30 0.18 "CONTINUOUS" "1719" "G")
  (list "1706" "RI-GWA_RIOOLPUT_BLINDEPUT_BETON" 30 0.18 "CONTINUOUS" "1705" "G")
  (list "1707" "RI-GWA_RIOOLPUT_BLINDEPUT_PE" 30 0.18 "CONTINUOUS" "1705" "G")
  (list "1723" "RI-GWA_RIOOLPUT_STUWPUT_BETON" 30 0.18 "CONTINUOUS" "1722" "G")
  (list "1724" "RI-GWA_RIOOLPUT_STUWPUT_PE" 30 0.18 "CONTINUOUS" "1722" "G")
  (list "1726" "RI-GWA_RIOOLPUT_VALPUT_BETON" 30 0.18 "CONTINUOUS" "1725" "G")
  (list "1727" "RI-GWA_RIOOLPUT_VALPUT_PE" 30 0.18 "CONTINUOUS" "1725" "G")
  (list "1777" "RI-GWA_TRANSPORTLEIDING_PVC_160" 30 0.18 "RI-GWA-SO" "1776" "G")
  (list "3690" "RI-GWA_TRANSPORTLEIDING_PVC_125" 30 0.18 "RI-GWA-SO" "1776" "G")
  (list "1778" "RI-GWA_TRANSPORTLEIDING_PVC_200" 30 0.18 "RI-GWA-SO" "1776" "G")
  (list "1783" "RI-GWA_TRANSPORTLEIDING_PVC_630" 30 0.18 "RI-GWA-SO" "1776" "G")
  (list "1782" "RI-GWA_TRANSPORTLEIDING_PVC_500" 30 0.18 "RI-GWA-SO" "1776" "G")
  (list "1779" "RI-GWA_TRANSPORTLEIDING_PVC_250" 30 0.18 "RI-GWA-SO" "1776" "G")
  (list "1781" "RI-GWA_TRANSPORTLEIDING_PVC_400" 30 0.18 "RI-GWA-SO" "1776" "G")
  (list "1780" "RI-GWA_TRANSPORTLEIDING_PVC_315" 30 0.18 "RI-GWA-SO" "1776" "G")
  (list "1760" "RI-GWA_TRANSPORTLEIDING_GRES_300" 30 0.18 "RI-GWA-SO" "1756" "G")
  (list "1764" "RI-GWA_TRANSPORTLEIDING_GRES_700" 30 0.18 "RI-GWA-SO" "1756" "G")
  (list "1763" "RI-GWA_TRANSPORTLEIDING_GRES_600" 30 0.18 "RI-GWA-SO" "1756" "G")
  (list "1762" "RI-GWA_TRANSPORTLEIDING_GRES_500" 30 0.18 "RI-GWA-SO" "1756" "G")
  (list "1757" "RI-GWA_TRANSPORTLEIDING_GRES_1000" 30 0.18 "RI-GWA-SO" "1756" "G")
  (list "1765" "RI-GWA_TRANSPORTLEIDING_GRES_800" 30 0.18 "RI-GWA-SO" "1756" "G")
  (list "1759" "RI-GWA_TRANSPORTLEIDING_GRES_250" 30 0.18 "RI-GWA-SO" "1756" "G")
  (list "1761" "RI-GWA_TRANSPORTLEIDING_GRES_400" 30 0.18 "RI-GWA-SO" "1756" "G")
  (list "1766" "RI-GWA_TRANSPORTLEIDING_GRES_900" 30 0.18 "RI-GWA-SO" "1756" "G")
  (list "1758" "RI-GWA_TRANSPORTLEIDING_GRES_200" 30 0.18 "RI-GWA-SO" "1756" "G")
  (list "1736" "RI-GWA_TRANSPORTLEIDING_BETON_2000" 30 0.18 "RI-GWA-SO" "1732" "G")
  (list "1735" "RI-GWA_TRANSPORTLEIDING_BETON_1500" 30 0.18 "RI-GWA-SO" "1732" "G")
  (list "1733" "RI-GWA_TRANSPORTLEIDING_BETON_1000" 30 0.18 "RI-GWA-SO" "1732" "G")
  (list "1745" "RI-GWA_TRANSPORTLEIDING_BETON_EI" 30 0.18 "RI-GWA-SO" "1732" "G")
  (list "1734" "RI-GWA_TRANSPORTLEIDING_BETON_1250" 30 0.18 "RI-GWA-SO" "1732" "G")
  (list "1742" "RI-GWA_TRANSPORTLEIDING_BETON_700" 30 0.18 "RI-GWA-SO" "1732" "G")
  (list "1744" "RI-GWA_TRANSPORTLEIDING_BETON_900" 30 0.18 "RI-GWA-SO" "1732" "G")
  (list "1741" "RI-GWA_TRANSPORTLEIDING_BETON_600" 30 0.18 "RI-GWA-SO" "1732" "G")
  (list "1737" "RI-GWA_TRANSPORTLEIDING_BETON_250" 30 0.18 "RI-GWA-SO" "1732" "G")
  (list "1743" "RI-GWA_TRANSPORTLEIDING_BETON_800" 30 0.18 "RI-GWA-SO" "1732" "G")
  (list "1739" "RI-GWA_TRANSPORTLEIDING_BETON_400" 30 0.18 "RI-GWA-SO" "1732" "G")
  (list "1740" "RI-GWA_TRANSPORTLEIDING_BETON_500" 30 0.18 "RI-GWA-SO" "1732" "G")
  (list "1738" "RI-GWA_TRANSPORTLEIDING_BETON_300" 30 0.18 "RI-GWA-SO" "1732" "G")
  (list "1774" "RI-GWA_TRANSPORTLEIDING_PE_560" 30 0.18 "RI-GWA-SO" "1767" "G")
  (list "1772" "RI-GWA_TRANSPORTLEIDING_PE_450" 30 0.18 "RI-GWA-SO" "1767" "G")
  (list "1769" "RI-GWA_TRANSPORTLEIDING_PE_315" 30 0.18 "RI-GWA-SO" "1767" "G")
  (list "1768" "RI-GWA_TRANSPORTLEIDING_PE_160" 30 0.18 "RI-GWA-SO" "1767" "G")
  (list "1771" "RI-GWA_TRANSPORTLEIDING_PE_400" 30 0.18 "RI-GWA-SO" "1767" "G")
  (list "1770" "RI-GWA_TRANSPORTLEIDING_PE_355" 30 0.18 "RI-GWA-SO" "1767" "G")
  (list "1773" "RI-GWA_TRANSPORTLEIDING_PE_500" 30 0.18 "RI-GWA-SO" "1767" "G")
  (list "1775" "RI-GWA_TRANSPORTLEIDING_PE_630" 30 0.18 "RI-GWA-SO" "1767" "G")
  (list "3689" "RI-GWA_TRANSPORTLEIDING_PE_250" 30 0.18 "RI-GWA-SO" "1767" "G")
  (list "3644" "RI-GWA_RIOOLLEIDING_GRES_200" 30 0.18 "RI-GWA-SO" "3642" "G")
  (list "3648" "RI-GWA_RIOOLLEIDING_GRES_500" 30 0.18 "RI-GWA-SO" "3642" "G")
  (list "3647" "RI-GWA_RIOOLLEIDING_GRES_400" 30 0.18 "RI-GWA-SO" "3642" "G")
  (list "3643" "RI-GWA_RIOOLLEIDING_GRES_1000" 30 0.18 "RI-GWA-SO" "3642" "G")
  (list "3649" "RI-GWA_RIOOLLEIDING_GRES_600" 30 0.18 "RI-GWA-SO" "3642" "G")
  (list "3651" "RI-GWA_RIOOLLEIDING_GRES_800" 30 0.18 "RI-GWA-SO" "3642" "G")
  (list "3652" "RI-GWA_RIOOLLEIDING_GRES_900" 30 0.18 "RI-GWA-SO" "3642" "G")
  (list "3645" "RI-GWA_RIOOLLEIDING_GRES_250" 30 0.18 "RI-GWA-SO" "3642" "G")
  (list "3646" "RI-GWA_RIOOLLEIDING_GRES_300" 30 0.18 "RI-GWA-SO" "3642" "G")
  (list "3650" "RI-GWA_RIOOLLEIDING_GRES_700" 30 0.18 "RI-GWA-SO" "3642" "G")
  (list "3622" "RI-GWA_RIOOLLEIDING_BETON_2000" 30 0.18 "RI-GWA-SO" "3618" "G")
  (list "3624" "RI-GWA_RIOOLLEIDING_BETON_300" 30 0.18 "RI-GWA-SO" "3618" "G")
  (list "3620" "RI-GWA_RIOOLLEIDING_BETON_1250" 30 0.18 "RI-GWA-SO" "3618" "G")
  (list "3631" "RI-GWA_RIOOLLEIDING_BETON_EI" 30 0.18 "RI-GWA-SO" "3618" "G")
  (list "3625" "RI-GWA_RIOOLLEIDING_BETON_400" 30 0.18 "RI-GWA-SO" "3618" "G")
  (list "3626" "RI-GWA_RIOOLLEIDING_BETON_500" 30 0.18 "RI-GWA-SO" "3618" "G")
  (list "3629" "RI-GWA_RIOOLLEIDING_BETON_800" 30 0.18 "RI-GWA-SO" "3618" "G")
  (list "3627" "RI-GWA_RIOOLLEIDING_BETON_600" 30 0.18 "RI-GWA-SO" "3618" "G")
  (list "3630" "RI-GWA_RIOOLLEIDING_BETON_900" 30 0.18 "RI-GWA-SO" "3618" "G")
  (list "3619" "RI-GWA_RIOOLLEIDING_BETON_1000" 30 0.18 "RI-GWA-SO" "3618" "G")
  (list "3621" "RI-GWA_RIOOLLEIDING_BETON_1500" 30 0.18 "RI-GWA-SO" "3618" "G")
  (list "3628" "RI-GWA_RIOOLLEIDING_BETON_700" 30 0.18 "RI-GWA-SO" "3618" "G")
  (list "3623" "RI-GWA_RIOOLLEIDING_BETON_250" 30 0.18 "RI-GWA-SO" "3618" "G")
  (list "3664" "RI-GWA_RIOOLLEIDING_PVC_200" 30 0.18 "RI-GWA-SO" "3662" "G")
  (list "3668" "RI-GWA_RIOOLLEIDING_PVC_500" 30 0.18 "RI-GWA-SO" "3662" "G")
  (list "3667" "RI-GWA_RIOOLLEIDING_PVC_400" 30 0.18 "RI-GWA-SO" "3662" "G")
  (list "3665" "RI-GWA_RIOOLLEIDING_PVC_250" 30 0.18 "RI-GWA-SO" "3662" "G")
  (list "3663" "RI-GWA_RIOOLLEIDING_PVC_160" 30 0.18 "RI-GWA-SO" "3662" "G")
  (list "3666" "RI-GWA_RIOOLLEIDING_PVC_315" 30 0.18 "RI-GWA-SO" "3662" "G")
  (list "3669" "RI-GWA_RIOOLLEIDING_PVC_630" 30 0.18 "RI-GWA-SO" "3662" "G")
  (list "3658" "RI-GWA_RIOOLLEIDING_PE_450" 30 0.18 "RI-GWA-SO" "3653" "G")
  (list "3656" "RI-GWA_RIOOLLEIDING_PE_355" 30 0.18 "RI-GWA-SO" "3653" "G")
  (list "3654" "RI-GWA_RIOOLLEIDING_PE_160" 30 0.18 "RI-GWA-SO" "3653" "G")
  (list "3657" "RI-GWA_RIOOLLEIDING_PE_400" 30 0.18 "RI-GWA-SO" "3653" "G")
  (list "3661" "RI-GWA_RIOOLLEIDING_PE_630" 30 0.18 "RI-GWA-SO" "3653" "G")
  (list "3660" "RI-GWA_RIOOLLEIDING_PE_560" 30 0.18 "RI-GWA-SO" "3653" "G")
  (list "3659" "RI-GWA_RIOOLLEIDING_PE_500" 30 0.18 "RI-GWA-SO" "3653" "G")
  (list "3655" "RI-GWA_RIOOLLEIDING_PE_315" 30 0.18 "RI-GWA-SO" "3653" "G")
  (list "1714" "RI-GWA_AANSLUITPUT_ONTSTOPPINGSPUT_BETON" 30 0.18 "CONTINUOUS" "1713" "G")
  (list "1715" "RI-GWA_AANSLUITPUT_ONTSTOPPINGSPUT_PE" 30 0.18 "CONTINUOUS" "1713" "G")
  (list "1669" "RI-GWA_PERCEELAANSLUITLEIDING_GRES_100" 30 0.18 "RI-GWA_AANSLUITLEIDING-SO" "1668" "G")
  (list "1670" "RI-GWA_PERCEELAANSLUITLEIDING_GRES_125" 30 0.18 "RI-GWA_AANSLUITLEIDING-SO" "1668" "G")
  (list "1671" "RI-GWA_PERCEELAANSLUITLEIDING_GRES_150" 30 0.18 "RI-GWA_AANSLUITLEIDING-SO" "1668" "G")
  (list "1676" "RI-GWA_PERCEELAANSLUITLEIDING_PE_90" 30 0.18 "RI-GWA_AANSLUITLEIDING-SO" "1672" "G")
  (list "1674" "RI-GWA_PERCEELAANSLUITLEIDING_PE_63" 30 0.18 "RI-GWA_AANSLUITLEIDING-SO" "1672" "G")
  (list "1673" "RI-GWA_PERCEELAANSLUITLEIDING_PE_110" 30 0.18 "RI-GWA_AANSLUITLEIDING-SO" "1672" "G")
  (list "1675" "RI-GWA_PERCEELAANSLUITLEIDING_PE_75" 30 0.18 "RI-GWA_AANSLUITLEIDING-SO" "1672" "G")
  (list "1678" "RI-GWA_PERCEELAANSLUITLEIDING_PVC_110" 30 0.18 "RI-GWA_AANSLUITLEIDING-SO" "1677" "G")
  (list "1680" "RI-GWA_PERCEELAANSLUITLEIDING_PVC_160" 30 0.18 "RI-GWA_AANSLUITLEIDING-SO" "1677" "G")
  (list "1679" "RI-GWA_PERCEELAANSLUITLEIDING_PVC_125" 30 0.18 "RI-GWA_AANSLUITLEIDING-SO" "1677" "G")
  (list "1694" "RI-GWA_KOLKAANSLUITLEIDING_PE_160" 30 0.18 "RI-GWA_AANSLUITLEIDING-SO" "1691" "G")
  (list "1693" "RI-GWA_KOLKAANSLUITLEIDING_PE_125" 30 0.18 "RI-GWA_AANSLUITLEIDING-SO" "1691" "G")
  (list "1692" "RI-GWA_KOLKAANSLUITLEIDING_PE_110" 30 0.18 "RI-GWA_AANSLUITLEIDING-SO" "1691" "G")
  (list "1697" "RI-GWA_KOLKAANSLUITLEIDING_PVC_125" 30 0.18 "RI-GWA_AANSLUITLEIDING-SO" "1695" "G")
  (list "1696" "RI-GWA_KOLKAANSLUITLEIDING_PVC_110" 30 0.18 "RI-GWA_AANSLUITLEIDING-SO" "1695" "G")
  (list "1698" "RI-GWA_KOLKAANSLUITLEIDING_PVC_160" 30 0.18 "RI-GWA_AANSLUITLEIDING-SO" "1695" "G")
  (list "3597" "RI-DRAINAGE_PUT_DOORSPUITPUT_PE" 90 0.18 "CONTINUOUS" "1657" "G")
  (list "3596" "RI-DRAINAGE_PUT_DOORSPUITPUT_BETON" 90 0.18 "CONTINUOUS" "1657" "G")
  (list "3595" "RI-DRAINAGE_PUT_DRAINAGEPUT_PE" 90 0.18 "CONTINUOUS" "3593" "G")
  (list "3594" "RI-DRAINAGE_PUT_DRAINAGEPUT_BETON" 90 0.18 "CONTINUOUS" "3593" "G")
  (list "1643" "RI-DRAINAGE_DRAIN_PP_200" 90 0.18 "RI-DRAINAGE-SO" "1639" "G")
  (list "1644" "RI-DRAINAGE_DRAIN_PP_65" 90 0.18 "RI-DRAINAGE-SO" "1639" "G")
  (list "1641" "RI-DRAINAGE_DRAIN_PP_125" 90 0.18 "RI-DRAINAGE-SO" "1639" "G")
  (list "1645" "RI-DRAINAGE_DRAIN_PP_80" 90 0.18 "RI-DRAINAGE-SO" "1639" "G")
  (list "1640" "RI-DRAINAGE_DRAIN_PP_100" 90 0.18 "RI-DRAINAGE-SO" "1639" "G")
  (list "1642" "RI-DRAINAGE_DRAIN_PP_160" 90 0.18 "RI-DRAINAGE-SO" "1639" "G")
  (list "1648" "RI-DRAINAGE_DRAIN_PVC_125" 90 0.18 "RI-DRAINAGE-SO" "1646" "G")
  (list "1647" "RI-DRAINAGE_DRAIN_PVC_100" 90 0.18 "RI-DRAINAGE-SO" "1646" "G")
  (list "1652" "RI-DRAINAGE_DRAIN_PVC_80" 90 0.18 "RI-DRAINAGE-SO" "1646" "G")
  (list "1651" "RI-DRAINAGE_DRAIN_PVC_65" 90 0.18 "RI-DRAINAGE-SO" "1646" "G")
  (list "1650" "RI-DRAINAGE_DRAIN_PVC_200" 90 0.18 "RI-DRAINAGE-SO" "1646" "G")
  (list "1649" "RI-DRAINAGE_DRAIN_PVC_160" 90 0.18 "RI-DRAINAGE-SO" "1646" "G")
  (list "1838" "RI-HWA_RIOOLPUT_INSPECTIEPUT_HONDEHOKPUT_BETON" 150 0.18 "CONTINUOUS" "1837" "G")
  (list "1884" "RI-HWA_TRANSPORTLEIDING_BETON_EI_900X1350" 150 0.18 "RI-HWA-SO" "1874" "G")
  (list "1878" "RI-HWA_TRANSPORTLEIDING_BETON_EI_300X450" 150 0.18 "RI-HWA-SO" "1874" "G")
  (list "1877" "RI-HWA_TRANSPORTLEIDING_BETON_EI_250X375" 150 0.18 "RI-HWA-SO" "1874" "G")
  (list "1881" "RI-HWA_TRANSPORTLEIDING_BETON_EI_600X900" 150 0.18 "RI-HWA-SO" "1874" "G")
  (list "1876" "RI-HWA_TRANSPORTLEIDING_BETON_EI_200X300" 150 0.18 "RI-HWA-SO" "1874" "G")
  (list "1880" "RI-HWA_TRANSPORTLEIDING_BETON_EI_500X750" 150 0.18 "RI-HWA-SO" "1874" "G")
  (list "1883" "RI-HWA_TRANSPORTLEIDING_BETON_EI_800X1200" 150 0.18 "RI-HWA-SO" "1874" "G")
  (list "1879" "RI-HWA_TRANSPORTLEIDING_BETON_EI_400X600" 150 0.18 "RI-HWA-SO" "1874" "G")
  (list "1875" "RI-HWA_TRANSPORTLEIDING_BETON_EI_1000X1500" 150 0.18 "RI-HWA-SO" "1874" "G")
  (list "1882" "RI-HWA_TRANSPORTLEIDING_BETON_EI_700X1050" 150 0.18 "RI-HWA-SO" "1874" "G")
  (list "3729" "RI-HWA_RIOOLLEIDING_BETON_EI_400X600" 150 0.18 "RI-HWA-SO" "3724" "G")
  (list "3733" "RI-HWA_RIOOLLEIDING_BETON_EI_800X1200" 150 0.18 "RI-HWA-SO" "3724" "G")
  (list "3730" "RI-HWA_RIOOLLEIDING_BETON_EI_500X750" 150 0.18 "RI-HWA-SO" "3724" "G")
  (list "3731" "RI-HWA_RIOOLLEIDING_BETON_EI_600X900" 150 0.18 "RI-HWA-SO" "3724" "G")
  (list "3725" "RI-HWA_RIOOLLEIDING_BETON_EI_1000X1500" 150 0.18 "RI-HWA-SO" "3724" "G")
  (list "3726" "RI-HWA_RIOOLLEIDING_BETON_EI_200X300" 150 0.18 "RI-HWA-SO" "3724" "G")
  (list "3728" "RI-HWA_RIOOLLEIDING_BETON_EI_300X450" 150 0.18 "RI-HWA-SO" "3724" "G")
  (list "3727" "RI-HWA_RIOOLLEIDING_BETON_EI_250X375" 150 0.18 "RI-HWA-SO" "3724" "G")
  (list "3732" "RI-HWA_RIOOLLEIDING_BETON_EI_700X1050" 150 0.18 "RI-HWA-SO" "3724" "G")
  (list "3734" "RI-HWA_RIOOLLEIDING_BETON_EI_900X1350" 150 0.18 "RI-HWA-SO" "3724" "G")
  (list "3961" "RI-DWA_RIOOLLEIDING_BETON_EI_250X375" 20 0.18 "RI-DWA-SO" "3958" "G")
  (list "3959" "RI-DWA_RIOOLLEIDING_BETON_EI_1000X1500" 20 0.18 "RI-DWA-SO" "3958" "G")
  (list "3967" "RI-DWA_RIOOLLEIDING_BETON_EI_800X1200" 20 0.18 "RI-DWA-SO" "3958" "G")
  (list "3968" "RI-DWA_RIOOLLEIDING_BETON_EI_900X1350" 20 0.18 "RI-DWA-SO" "3958" "G")
  (list "3966" "RI-DWA_RIOOLLEIDING_BETON_EI_700X1050" 20 0.18 "RI-DWA-SO" "3958" "G")
  (list "3963" "RI-DWA_RIOOLLEIDING_BETON_EI_400X600" 20 0.18 "RI-DWA-SO" "3958" "G")
  (list "3960" "RI-DWA_RIOOLLEIDING_BETON_EI_200X300" 20 0.18 "RI-DWA-SO" "3958" "G")
  (list "3965" "RI-DWA_RIOOLLEIDING_BETON_EI_600X900" 20 0.18 "RI-DWA-SO" "3958" "G")
  (list "3964" "RI-DWA_RIOOLLEIDING_BETON_EI_500X750" 20 0.18 "RI-DWA-SO" "3958" "G")
  (list "3962" "RI-DWA_RIOOLLEIDING_BETON_EI_300X450" 20 0.18 "RI-DWA-SO" "3958" "G")
  (list "2256" "RI-DWA_RIOOLPUT_INSPECTIEPUT_HONDEHOKPUT_BETON" 20 0.18 "CONTINUOUS" "2255" "G")
  (list "2310" "RI-DWA_TRANSPORTLEIDING_BETON_EI_900X1350" 20 0.18 "RI-DWA-SO" "2300" "G")
  (list "2302" "RI-DWA_TRANSPORTLEIDING_BETON_EI_200X300" 20 0.18 "RI-DWA-SO" "2300" "G")
  (list "2308" "RI-DWA_TRANSPORTLEIDING_BETON_EI_700X1050" 20 0.18 "RI-DWA-SO" "2300" "G")
  (list "2306" "RI-DWA_TRANSPORTLEIDING_BETON_EI_500X750" 20 0.18 "RI-DWA-SO" "2300" "G")
  (list "2309" "RI-DWA_TRANSPORTLEIDING_BETON_EI_800X1200" 20 0.18 "RI-DWA-SO" "2300" "G")
  (list "2301" "RI-DWA_TRANSPORTLEIDING_BETON_EI_1000X1500" 20 0.18 "RI-DWA-SO" "2300" "G")
  (list "2305" "RI-DWA_TRANSPORTLEIDING_BETON_EI_400X600" 20 0.18 "RI-DWA-SO" "2300" "G")
  (list "2307" "RI-DWA_TRANSPORTLEIDING_BETON_EI_600X900" 20 0.18 "RI-DWA-SO" "2300" "G")
  (list "2304" "RI-DWA_TRANSPORTLEIDING_BETON_EI_300X450" 20 0.18 "RI-DWA-SO" "2300" "G")
  (list "2303" "RI-DWA_TRANSPORTLEIDING_BETON_EI_250X375" 20 0.18 "RI-DWA-SO" "2300" "G")
  (list "1709" "RI-GWA_RIOOLPUT_INSPECTIEPUT_HONDEHOKPUT_BETON" 30 0.18 "CONTINUOUS" "1708" "G")
  (list "1749" "RI-GWA_TRANSPORTLEIDING_BETON_EI_300X450" 30 0.18 "RI-GWA-SO" "1745" "G")
  (list "1746" "RI-GWA_TRANSPORTLEIDING_BETON_EI_1000X1500" 30 0.18 "RI-GWA-SO" "1745" "G")
  (list "1752" "RI-GWA_TRANSPORTLEIDING_BETON_EI_600X900" 30 0.18 "RI-GWA-SO" "1745" "G")
  (list "1748" "RI-GWA_TRANSPORTLEIDING_BETON_EI_250X375" 30 0.18 "RI-GWA-SO" "1745" "G")
  (list "1751" "RI-GWA_TRANSPORTLEIDING_BETON_EI_500X750" 30 0.18 "RI-GWA-SO" "1745" "G")
  (list "1755" "RI-GWA_TRANSPORTLEIDING_BETON_EI_900X1350" 30 0.18 "RI-GWA-SO" "1745" "G")
  (list "1753" "RI-GWA_TRANSPORTLEIDING_BETON_EI_700X1050" 30 0.18 "RI-GWA-SO" "1745" "G")
  (list "1750" "RI-GWA_TRANSPORTLEIDING_BETON_EI_400X600" 30 0.18 "RI-GWA-SO" "1745" "G")
  (list "1754" "RI-GWA_TRANSPORTLEIDING_BETON_EI_800X1200" 30 0.18 "RI-GWA-SO" "1745" "G")
  (list "1747" "RI-GWA_TRANSPORTLEIDING_BETON_EI_200X300" 30 0.18 "RI-GWA-SO" "1745" "G")
  (list "3638" "RI-GWA_RIOOLLEIDING_BETON_EI_600X900" 30 0.18 "RI-GWA-SO" "3631" "G")
  (list "3640" "RI-GWA_RIOOLLEIDING_BETON_EI_800X1200" 30 0.18 "RI-GWA-SO" "3631" "G")
  (list "3632" "RI-GWA_RIOOLLEIDING_BETON_EI_1000X1500" 30 0.18 "RI-GWA-SO" "3631" "G")
  (list "3637" "RI-GWA_RIOOLLEIDING_BETON_EI_500X750" 30 0.18 "RI-GWA-SO" "3631" "G")
  (list "3633" "RI-GWA_RIOOLLEIDING_BETON_EI_200X300" 30 0.18 "RI-GWA-SO" "3631" "G")
  (list "3634" "RI-GWA_RIOOLLEIDING_BETON_EI_250X375" 30 0.18 "RI-GWA-SO" "3631" "G")
  (list "3641" "RI-GWA_RIOOLLEIDING_BETON_EI_900X1350" 30 0.18 "RI-GWA-SO" "3631" "G")
  (list "3639" "RI-GWA_RIOOLLEIDING_BETON_EI_700X1050" 30 0.18 "RI-GWA-SO" "3631" "G")
  (list "3636" "RI-GWA_RIOOLLEIDING_BETON_EI_400X600" 30 0.18 "RI-GWA-SO" "3631" "G")
  (list "3635" "RI-GWA_RIOOLLEIDING_BETON_EI_300X450" 30 0.18 "RI-GWA-SO" "3631" "G")
  (list "2052" "RI-OVERIG" 10 0.18 "RI-OVERIG-SO" "" "G")
  (list "1786" "RI-HWA" 150 0.18 "RI-HWA-SO" "" "G")
  (list "1944" "RI-ITR" 50 0.18 "RI-ITR-SO" "" "G")
  (list "3451" "RI-RWZI" 90 0.18 "CONTINUOUS" "" "G")
  (list "2220" "RI-DWA" 20 0.18 "RI-DWA-SO" "" "G")
  (list "2194" "RI-VACUUMLEIDING" 10 0.18 "RI-VACUUM-SO" "" "G")
  (list "2054" "RI-PERSLEIDING" 210 0.18 "RI-PERS-SO" "" "G")
  (list "1664" "RI-GWA" 30 0.18 "RI-GWA-SO" "" "G")
  (list "1635" "RI-DRAINAGE" 90 0.18 "RI-DRAINAGE-SO" "" "G")
)) *nlcs-layers*))

; Staalconstructies (SC) - 21 lagen
(setq *nlcs-layers* (cons (list "SC" "Staalconstructies" (list
  (list "2868" "SC-VERBINDING_BOUT" 150 0.18 "CONTINUOUS" "2867" "G/A")
  (list "2869" "SC-VERBINDING_LAS" 210 0.18 "CONTINUOUS" "2867" "G/A")
  (list "2871" "SC-AANGRENZENDECONSTRUCTIE_BETON" 7 0.18 "CONTINUOUS" "2870" "G/A")
  (list "2872" "SC-AANGRENZENDECONSTRUCTIE_HOUT" 7 0.18 "CONTINUOUS" "2870" "G/A")
  (list "2873" "SC-AANGRENZENDECONSTRUCTIE_METSELWERK" 7 0.18 "CONTINUOUS" "2870" "G/A")
  (list "3478" "SC-STAALVORM_RVS" 150 0.18 "CONTINUOUS" "2862" "G/A")
  (list "2864" "SC-STAALVORM_PLAAT" 140 0.18 "CONTINUOUS" "2862" "G/A")
  (list "2863" "SC-STAALVORM_PROFIEL" 140 0.18 "CONTINUOUS" "2862" "G/A")
  (list "3480" "SC-STAALVORM_RVS_PROFIEL" 150 0.18 "CONTINUOUS" "3478" "G/A")
  (list "3479" "SC-STAALVORM_RVS_PLAAT" 150 0.18 "CONTINUOUS" "3478" "G/A")
  (list "2867" "SC-VERBINDING" 150 0.18 "CONTINUOUS" "" "G/A")
  (list "2866" "SC-HULPSTAAL" 140 0.18 "CONTINUOUS" "" "G/A")
  (list "2865" "SC-TREKSTANG" 140 0.18 "CONTINUOUS" "" "G/A")
  (list "2862" "SC-STAALVORM" 140 0.18 "CONTINUOUS" "" "G/A")
  (list "2870" "SC-AANGRENZENDECONSTRUCTIE" 7 0.18 "CONTINUOUS" "" "G")
  (list "2875" "SC-ITSO" 140 0.18 "CONTINUOUS" "" "G")
  (list "2874" "SC-OVERIGMATERIAAL" 7 0.18 "CONTINUOUS" "" "G")
  (list "2879" "SC-LEVENSDUURVERLENGENDE MAATREGEL" 170 0.18 "CONTINUOUS" "" "G")
  (list "2876" "SC-NAAD" 150 0.18 "CONTINUOUS" "" "G")
  (list "2878" "SC-REPARATIES" 170 0.18 "CONTINUOUS" "" "G")
  (list "2877" "SC-SLOOPLIJN" 10 0.18 "CONTINUOUS" "" "G")
)) *nlcs-layers*))

; Verhardingen (VH) - 229 lagen
(setq *nlcs-layers* (cons (list "VH" "Verhardingen" (list
  (list "2482" "VH-GESLOTENVERHARDING_BENTONIET" 10 0.18 "CONTINUOUS" "3342" "G/S/A")
  (list "2517" "VH-GESLOTENVERHARDING_METSELWERK" 10 0.18 "CONTINUOUS" "3342" "G/S/A")
  (list "2473" "VH-OPENVERHARDING_BASALT" 90 0.18 "CONTINUOUS" "2519" "G/S/A")
  (list "2518" "VH-OPENVERHARDING_NATUURSTEEN" 90 0.18 "CONTINUOUS" "2519" "G/S/A")
  (list "2516" "VH-OPENVERHARDING_KALKZANDSTEEN" 90 0.18 "CONTINUOUS" "2519" "G/S/A")
  (list "2515" "VH-OPENVERHARDING_HSTEEN" 90 0.18 "CONTINUOUS" "2519" "G/S/A")
  (list "2491" "VH-OPENVERHARDING_DELTA" 90 0.18 "CONTINUOUS" "2519" "G/S/A")
  (list "2521" "VH-OPENVERHARDING_PLANKEN" 90 0.18 "CONTINUOUS" "2519" "G/S/A")
  (list "2490" "VH-OPENVERHARDING_COBBLESTONE" 90 0.18 "CONTINUOUS" "2519" "G/S/A")
  (list "2506" "VH-HALFVERHARDING_GESTABILISEERD GRAS" 130 0.18 "CONTINUOUS" "2511" "G/S/A")
  (list "2509" "VH-HALFVERHARDING_GRASPLAAT" 130 0.18 "CONTINUOUS" "2511" "G/S/A")
  (list "2483" "VH-HALFVERHARDING_BESTORTING" 130 0.18 "CONTINUOUS" "2511" "G/S/A")
  (list "2514" "VH-ONVERHARD_HOUTSNIPPERS" 210 0.18 "CONTINUOUS" "2936" "G/S/A")
  (list "2533" "VH-OPENVERHARDING_TEGEL_SIER" 90 0.18 "CONTINUOUS" "2531" "G/S/A")
  (list "2534" "VH-OPENVERHARDING_TEGEL_GRAS" 70 0.18 "CONTINUOUS" "2531" "G/S/A")
  (list "2484" "VH-GESLOTENVERHARDING_BETON" 10 0.18 "CONTINUOUS" "3342" "G/S/A")
  (list "2464" "VH-GESLOTENVERHARDING_ASFALT" 10 0.18 "CONTINUOUS" "3342" "G/S/A")
  (list "2529" "VH-OPENVERHARDING_STRAATBAKSTEEN" 90 0.18 "CONTINUOUS" "2519" "G/S/A")
  (list "2531" "VH-OPENVERHARDING_TEGEL" 90 0.18 "CONTINUOUS" "2519" "G/S/A")
  (list "2524" "VH-OPENVERHARDING_SIERBESTRATING" 90 0.18 "CONTINUOUS" "2519" "G/S/A")
  (list "2488" "VH-OPENVERHARDING_BETONSTRAATSTEEN" 90 0.18 "CONTINUOUS" "2519" "G/S/A")
  (list "3484" "VH-HALFVERHARDING_GRAVEL" 130 0.18 "CONTINUOUS" "2511" "G/S/A")
  (list "2522" "VH-HALFVERHARDING_PUIN" 130 0.18 "CONTINUOUS" "2511" "G/S/A")
  (list "2508" "VH-HALFVERHARDING_GRASBETONSTEEN" 130 0.18 "CONTINUOUS" "2511" "G/S/A")
  (list "2505" "VH-GEOTEXTIEL" 60 0.18 "CONTINUOUS" "" "")
  (list "2525" "VH-SPECIAAL" 150 0.18 "CONTINUOUS" "" "")
  (list "2523" "VH-ROOSTER" 150 0.18 "CONTINUOUS" "" "")
  (list "2492" "VH-FUNDERING" 7 0.18 "CONTINUOUS" "" "")
  (list "2472" "VH-OPENVERHARDING_BASALTON" 90 0.18 "CONTINUOUS" "2519" "G/S/A")
  (list "2397" "VH-KANTOPSLUITING_OPSLUITBAND" 150 0.18 "VH-OPSLUITBAND-SO" "2360" "G/S")
  (list "2416" "VH-KANTOPSLUITING_RIJWIELPADBAND" 10 0.18 "VH-RIJWIELPADBAND-SO" "2360" "G/S")
  (list "2364" "VH-KANTOPSLUITING_BUSHALTEBAND" 30 0.18 "VH-BUSHALTEBAND-SO" "2360" "G/S")
  (list "2422" "VH-KANTOPSLUITING_SCHEIDINGSBAND" 190 0.18 "VH-SCHEIDINGSBAND-SO" "2360" "G/S")
  (list "2438" "VH-KANTOPSLUITING_TALUDBAND" 60 0.18 "VH-TALUDBAND-SO" "2360" "G/S")
  (list "2396" "VH-KANTOPSLUITING_LEICONBLOK" 7 0.18 "VH-LEICON-SO" "2360" "G/S")
  (list "2394" "VH-KANTOPSLUITING_HAVENBAND" 140 0.18 "VH-HAVENBAND-SO" "2360" "G/S")
  (list "2409" "VH-KANTOPSLUITING_PLAKBAND" 210 0.18 "CONTINUOUS" "2360" "G/S")
  (list "4092" "VH-KANTOPSLUITING_ASFALTBAND" 240 0.18 "VH-ASFALTBAND-SO" "2360" "G/S")
  (list "2439" "VH-KANTOPSLUITING_TROTTOIRBAND" 210 0.18 "VH-TROTTOIRBAND-SO" "2360" "G/S")
  (list "2377" "VH-KANTOPSLUITING_GAZONBAND" 90 0.18 "VH-GAZONBAND-SO" "2360" "G/S")
  (list "2386" "VH-KANTOPSLUITING_GELEIDEBAND" 20 0.18 "VH-GELEIDEBAND-SO" "2360" "G/S")
  (list "2420" "VH-KANTOPSLUITING_ROTONDEBLOK" 210 0.18 "CONTINUOUS" "2360" "G/S")
  (list "2433" "VH-KANTOPSLUITING_SIGNALERINGSBAND" 210 0.18 "VH-SIGNALERINGSBAND-SO" "2360" "G/S")
  (list "2413" "VH-KANTOPSLUITING_PWSBAND" 120 0.18 "VH-PWSBAND-SO" "2360" "G/S")
  (list "2437" "VH-KANTOPSLUITING_STOOTBAND" 7 0.18 "CONTINUOUS" "2360" "G/S")
  (list "3341" "VH-HALFVERHARDING_FLOWBLOCK" 130 0.18 "CONTINUOUS" "2511" "G/A")
  (list "2940" "VH-GOOT_TEGEL" 170 0.18 "CONTINUOUS" "2348" "G/S")
  (list "2359" "VH-GOOT_ZOAB" 170 0.18 "CONTINUOUS" "2348" "G/S")
  (list "2346" "VH-DREMPEL_PREFAB_ELEMENT" 30 0.18 "CONTINUOUS" "2345" "G/S")
  (list "2532" "VH-OPENVERHARDING_TEGEL_RUBBER" 90 0.18 "CONTINUOUS" "2531" "G/S")
  (list "2376" "VH-KANTOPSLUITING_ELEMENT_VERLOOPBAND" 40 0.18 "CONTINUOUS" "2366" "G/S")
  (list "2370" "VH-KANTOPSLUITING_ELEMENT_INRIT" 40 0.18 "CONTINUOUS" "2366" "G/S")
  (list "3392" "VH-KANTOPSLUITING_ELEMENT_BOOMKRANS" 40 0.18 "CONTINUOUS" "2366" "G/S")
  (list "2367" "VH-KANTOPSLUITING_ELEMENT_BOOMKRANSBAND" 40 0.18 "VH-BOOMKRANSBAND-SO" "2366" "G/S")
  (list "2372" "VH-KANTOPSLUITING_ELEMENT_INRITBAND" 40 0.18 "CONTINUOUS" "2366" "G/S")
  (list "2369" "VH-KANTOPSLUITING_ELEMENT_HOEKSTUK" 40 0.18 "CONTINUOUS" "2366" "G/S")
  (list "2368" "VH-KANTOPSLUITING_ELEMENT_HOEKBLOK" 40 0.18 "CONTINUOUS" "2366" "G/S")
  (list "2450" "VH-KANTOPSLUITING_TROTTOIRBAND_RWS" 210 0.18 "VH-RWSBAND-SO" "2439" "G/S")
  (list "2371" "VH-KANTOPSLUITING_ELEMENT_INRIT_PERRONBAND" 40 0.18 "CONTINUOUS" "2370" "G/S")
  (list "3342" "VH-GESLOTENVERHARDING" 10 0.18 "CONTINUOUS" "" "")
  (list "2511" "VH-HALFVERHARDING" 130 0.18 "CONTINUOUS" "" "")
  (list "2512" "VH-HALFVERHARDING_GRIND" 130 0.18 "CONTINUOUS" "2511" "G/S")
  (list "3050" "VH-STOOTBAND" 7 0.18 "CONTINUOUS" "" "")
  (list "2348" "VH-GOOT" 170 0.18 "CONTINUOUS" "" "")
  (list "3051" "VH-VERKEERSTEGEL" 7 0.18 "CONTINUOUS" "" "")
  (list "4091" "VH-HERSTRATEN" 7 0.18 "CONTINUOUS" "" "")
  (list "2345" "VH-DREMPEL_PREFAB" 30 0.18 "CONTINUOUS" "2342" "G")
  (list "2343" "VH-DREMPEL_ASFALT" 30 0.18 "CONTINUOUS" "2342" "G")
  (list "2344" "VH-DREMPEL_BESTRAAT" 30 0.18 "CONTINUOUS" "2342" "G")
  (list "2347" "VH-DREMPEL_TALUD" 30 0.18 "CONTINUOUS" "2342" "G")
  (list "2937" "VH-GESLOTENVERHARDING_VLOEISTOFDICHT" 10 0.18 "CONTINUOUS" "3342" "G")
  (list "2460" "VH-KANTVERHARDING_ROLLAAG" 60 0.18 "CONTINUOUS" "2456" "G")
  (list "2457" "VH-KANTVERHARDING_TEGEL" 60 0.18 "CONTINUOUS" "2456" "G")
  (list "2461" "VH-KANTVERHARDING_STREKLAAG" 60 0.18 "CONTINUOUS" "2456" "G")
  (list "2366" "VH-KANTOPSLUITING_ELEMENT" 40 0.18 "CONTINUOUS" "2360" "G")
  (list "2410" "VH-KANTOPSLUITING_PLATEAUBAND" 30 0.18 "VH-PLATEAUBAND-SO" "2360" "G")
  (list "2362" "VH-KANTOPSLUITING_AMSTELBAND" 60 0.18 "VH-AMSTELBAND-SO" "2360" "G/S")
  (list "2455" "VH-KANTOPSLUITING_VOORKANTBAND" 50 0.18 "CONTINUOUS" "2360" "G")
  (list "2361" "VH-KANTOPSLUITING_ACHTERKANTBAND" 50 0.18 "CONTINUOUS" "2360" "G")
  (list "2395" "VH-KANTOPSLUITING_INRITBAND" 210 0.18 "CONTINUOUS" "2360" "G")
  (list "2939" "VH-HALFVERHARDING_KOPERSLAK" 130 0.18 "CONTINUOUS" "2511" "G")
  (list "2477" "VH-BEDRIJFSVLOERPLAAT_HOUT" 170 0.18 "CONTINUOUS" "2474" "G")
  (list "2479" "VH-BEDRIJFSVLOERPLAAT_STAAL" 170 0.18 "CONTINUOUS" "2474" "G")
  (list "2475" "VH-BEDRIJFSVLOERPLAAT_BETON" 170 0.18 "CONTINUOUS" "2474" "G")
  (list "2478" "VH-BEDRIJFSVLOERPLAAT_KUNSTSTOF" 170 0.18 "CONTINUOUS" "2474" "G")
  (list "2938" "VH-ONVERHARD_KLEI" 210 0.18 "CONTINUOUS" "2936" "G")
  (list "2526" "VH-SPECIAAL_SPORT" 90 0.18 "CONTINUOUS" "2525" "G/S")
  (list "2350" "VH-GOOT_BETON" 170 0.18 "CONTINUOUS" "2348" "G")
  (list "2353" "VH-GOOT_BSS" 170 0.18 "CONTINUOUS" "2348" "G")
  (list "2349" "VH-GOOT_ASFALT" 170 0.18 "CONTINUOUS" "2348" "G")
  (list "2356" "VH-GOOT_STRAATBAKSTEEN" 170 0.18 "CONTINUOUS" "2348" "G")
  (list "2500" "VH-FUNDERING_SLAKKEN" 7 0.18 "CONTINUOUS" "2492" "G")
  (list "2495" "VH-FUNDERING_GRANULAAT" 7 0.18 "CONTINUOUS" "2492" "G")
  (list "2504" "VH-FUNDERING_ZANDCEMENTSTABILISATIE" 7 0.18 "CONTINUOUS" "2492" "G")
  (list "2494" "VH-FUNDERING_EPS" 7 0.18 "CONTINUOUS" "2492" "G")
  (list "2499" "VH-FUNDERING_SCHUIMBETON" 7 0.18 "CONTINUOUS" "2492" "G")
  (list "2493" "VH-FUNDERING_BIMS" 7 0.18 "CONTINUOUS" "2492" "G")
  (list "2503" "VH-FUNDERING_ZAND" 7 0.18 "CONTINUOUS" "2492" "G")
  (list "2487" "VH-GESLOTENVERHARDING_BETON_SCHRAAL" 10 0.18 "CONTINUOUS" "2484" "G")
  (list "2485" "VH-GESLOTENVERHARDING_BETON_GEWAPEND" 10 0.18 "CONTINUOUS" "2484" "G")
  (list "2486" "VH-GESLOTENVERHARDING_BETON_ONGEWAPEND" 10 0.18 "CONTINUOUS" "2484" "G")
  (list "2944" "VH-GESLOTENVERHARDING_ASFALT-TRAPSGEWIJSFREZEN" 10 0.18 "VH-TRAPSGEWIJSFREZEN-SO" "2464" "G")
  (list "3014" "VH-GESLOTENVERHARDING_ASFALT_DEKLAAG" 10 0.18 "CONTINUOUS" "2464" "G")
  (list "2468" "VH-GESLOTENVERHARDING_ASFALT_ROOD" 10 0.18 "CONTINUOUS" "2464" "G")
  (list "2466" "VH-GESLOTENVERHARDING_ASFALT_GIETASFALT" 10 0.18 "CONTINUOUS" "2464" "G")
  (list "2942" "VH-GESLOTENVERHARDING_ASFALT_SLIJTLAAG" 10 0.18 "CONTINUOUS" "2464" "G")
  (list "3011" "VH-GESLOTENVERHARDING_ASFALT_ONDERLAAG" 10 0.18 "CONTINUOUS" "2464" "G")
  (list "2941" "VH-GESLOTENVERHARDING_ASFALT_COATING" 10 0.18 "CONTINUOUS" "2464" "G")
  (list "3015" "VH-GESLOTENVERHARDING_ASFALT_TUSSENLAAG" 10 0.18 "CONTINUOUS" "2464" "G")
  (list "2469" "VH-GESLOTENVERHARDING_ASFALT_WIT" 10 0.18 "CONTINUOUS" "2464" "G")
  (list "3010" "VH-GESLOTENVERHARDING_ASFALT_FUNDERING" 10 0.18 "CONTINUOUS" "2464" "G")
  (list "2467" "VH-GESLOTENVERHARDING_ASFALT_GROEN" 10 0.18 "CONTINUOUS" "2464" "G")
  (list "2471" "VH-GESLOTENVERHARDING_ASFALT_ZOAB" 10 0.18 "CONTINUOUS" "2464" "G")
  (list "2459" "VH-KANTVERHARDING_TEGEL_HALF" 60 0.18 "CONTINUOUS" "2457" "G")
  (list "2458" "VH-KANTVERHARDING_TEGEL_PAS" 60 0.18 "CONTINUOUS" "2457" "G")
  (list "3107" "VH-OPENVERHARDING_TEGEL_ZINLOOS GEWELD TEGEL" 7 0.18 "CONTINUOUS" "2531" "G")
  (list "2399" "VH-KANTOPSLUITING_OPSLUITBAND_60X200" 150 0.18 "VH-OPSLUITBAND-SO" "2397" "G")
  (list "2407" "VH-KANTOPSLUITING_OPSLUITBAND_150X400" 150 0.18 "VH-OPSLUITBAND-SO" "2397" "G")
  (list "2406" "VH-KANTOPSLUITING_OPSLUITBAND_150X300" 150 0.18 "VH-OPSLUITBAND-SO" "2397" "G")
  (list "2404" "VH-KANTOPSLUITING_OPSLUITBAND_120X250" 150 0.18 "VH-OPSLUITBAND-SO" "2397" "G")
  (list "2401" "VH-KANTOPSLUITING_OPSLUITBAND_100X200" 150 0.18 "VH-OPSLUITBAND-SO" "2397" "G")
  (list "2405" "VH-KANTOPSLUITING_OPSLUITBAND_150X250" 150 0.18 "VH-OPSLUITBAND-SO" "2397" "G")
  (list "2402" "VH-KANTOPSLUITING_OPSLUITBAND_100X300" 150 0.18 "VH-OPSLUITBAND-SO" "2397" "G")
  (list "2403" "VH-KANTOPSLUITING_OPSLUITBAND_100X400" 150 0.18 "VH-OPSLUITBAND-SO" "2397" "G")
  (list "2400" "VH-KANTOPSLUITING_OPSLUITBAND_80X200" 150 0.18 "VH-OPSLUITBAND-SO" "2397" "G")
  (list "2398" "VH-KANTOPSLUITING_OPSLUITBAND_60X150" 150 0.18 "VH-OPSLUITBAND-SO" "2397" "G")
  (list "2375" "VH-KANTOPSLUITING_ELEMENT_PUNTSTUK" 40 0.18 "CONTINUOUS" "2366" "G")
  (list "2374" "VH-KANTOPSLUITING_ELEMENT_PERRONBAND" 40 0.18 "CONTINUOUS" "2366" "G")
  (list "3080" "VH-KANTOPSLUITING_ELEMENT_VERLAAGDEBAND" 40 0.18 "CONTINUOUS" "2366" "G")
  (list "2373" "VH-KANTOPSLUITING_ELEMENT_PARKEERBAND" 40 0.18 "CONTINUOUS" "2366" "G")
  (list "2418" "VH-KANTOPSLUITING_RIJWIELPADBAND_410X250" 10 0.18 "VH-RIJWIELPADBAND-SO" "2416" "G")
  (list "2417" "VH-KANTOPSLUITING_RIJWIELPADBAND_380X200" 10 0.18 "VH-RIJWIELPADBAND-SO" "2416" "G")
  (list "2427" "VH-KANTOPSLUITING_SCHEIDINGSBAND_160X200" 190 0.18 "VH-SCHEIDINGSBAND-SO" "2422" "G")
  (list "2431" "VH-KANTOPSLUITING_SCHEIDINGSBAND_470X500" 190 0.18 "VH-SCHEIDINGSBAND-SO" "2422" "G")
  (list "2429" "VH-KANTOPSLUITING_SCHEIDINGSBAND_220X440" 190 0.18 "VH-SCHEIDINGSBAND-SO" "2422" "G")
  (list "2430" "VH-KANTOPSLUITING_SCHEIDINGSBAND_360X400" 190 0.18 "VH-SCHEIDINGSBAND-SO" "2422" "G")
  (list "2425" "VH-KANTOPSLUITING_SCHEIDINGSBAND_120X350" 190 0.18 "VH-SCHEIDINGSBAND-SO" "2422" "G")
  (list "2423" "VH-KANTOPSLUITING_SCHEIDINGSBAND_100X300" 190 0.18 "VH-SCHEIDINGSBAND-SO" "2422" "G")
  (list "2424" "VH-KANTOPSLUITING_SCHEIDINGSBAND_110X250" 190 0.18 "VH-SCHEIDINGSBAND-SO" "2422" "G")
  (list "2426" "VH-KANTOPSLUITING_SCHEIDINGSBAND_150X390" 190 0.18 "VH-SCHEIDINGSBAND-SO" "2422" "G")
  (list "2428" "VH-KANTOPSLUITING_SCHEIDINGSBAND_200X400" 190 0.18 "VH-SCHEIDINGSBAND-SO" "2422" "G")
  (list "2411" "VH-KANTOPSLUITING_PLATEAUBAND_60X120" 30 0.18 "VH-PLATEAUBAND-SO" "2410" "G")
  (list "4094" "VH-KANTOPSLUITING_ASFALTBAND_50X200X150" 240 0.18 "VH-ASFALTBAND-SO" "4092" "G")
  (list "4096" "VH-KANTOPSLUITING_ASFALTBAND_50X200X250" 240 0.18 "VH-ASFALTBAND-SO" "4092" "G")
  (list "4095" "VH-KANTOPSLUITING_ASFALTBAND_50X200X200" 240 0.18 "VH-ASFALTBAND-SO" "4092" "G")
  (list "2443" "VH-KANTOPSLUITING_TROTTOIRBAND_180X200" 210 0.18 "VH-TROTTOIRBAND-SO" "2439" "G")
  (list "2440" "VH-KANTOPSLUITING_TROTTOIRBAND_130X150" 210 0.18 "VH-TROTTOIRBAND-SO" "2439" "G")
  (list "2447" "VH-KANTOPSLUITING_TROTTOIRBAND_280X300" 210 0.18 "VH-TROTTOIRBAND-SO" "2439" "G")
  (list "2382" "VH-KANTOPSLUITING_GAZONBAND_120X200" 90 0.18 "VH-GAZONBAND-SO" "2377" "G")
  (list "2380" "VH-KANTOPSLUITING_GAZONBAND_100X200" 90 0.18 "VH-GAZONBAND-SO" "2377" "G")
  (list "2379" "VH-KANTOPSLUITING_GAZONBAND_80X200" 90 0.18 "VH-GAZONBAND-SO" "2377" "G")
  (list "2378" "VH-KANTOPSLUITING_GAZONBAND_60X200" 90 0.18 "VH-GAZONBAND-SO" "2377" "G")
  (list "2383" "VH-KANTOPSLUITING_GAZONBAND_120X250" 90 0.18 "VH-GAZONBAND-SO" "2377" "G")
  (list "2381" "VH-KANTOPSLUITING_GAZONBAND_100X300" 90 0.18 "VH-GAZONBAND-SO" "2377" "G")
  (list "2384" "VH-KANTOPSLUITING_GAZONBAND_150X400" 90 0.18 "VH-GAZONBAND-SO" "2377" "G")
  (list "2391" "VH-KANTOPSLUITING_GELEIDEBAND_70X200" 20 0.18 "VH-GELEIDEBAND-SO" "2386" "G")
  (list "2389" "VH-KANTOPSLUITING_GELEIDEBAND_60X120" 20 0.18 "VH-GELEIDEBAND-SO" "2386" "G")
  (list "2392" "VH-KANTOPSLUITING_GELEIDEBAND_80X160" 20 0.18 "VH-GELEIDEBAND-SO" "2386" "G")
  (list "2388" "VH-KANTOPSLUITING_GELEIDEBAND_50X200" 20 0.18 "VH-GELEIDEBAND-SO" "2386" "G")
  (list "2390" "VH-KANTOPSLUITING_GELEIDEBAND_70X150" 20 0.18 "VH-GELEIDEBAND-SO" "2386" "G")
  (list "2387" "VH-KANTOPSLUITING_GELEIDEBAND_50X150" 20 0.18 "VH-GELEIDEBAND-SO" "2386" "G")
  (list "2421" "VH-KANTOPSLUITING_ROTONDEBLOK_500 200" 210 0.18 "CONTINUOUS" "2420" "G")
  (list "2434" "VH-KANTOPSLUITING_SIGNALERINGSBAND_LED" 210 0.18 "VH-SIGNALERINGSBAND-SO" "2433" "G")
  (list "2435" "VH-KANTOPSLUITING_SIGNALERINGSBAND_LIJNREFLECTOR" 210 0.18 "VH-SIGNALERINGSBAND-SO" "2433" "G")
  (list "2436" "VH-KANTOPSLUITING_SIGNALERINGSBAND_OOG" 210 0.18 "VH-SIGNALERINGSBAND-SO" "2433" "G")
  (list "2414" "VH-KANTOPSLUITING_PWSBAND_250X130" 120 0.18 "VH-PWSBAND-SO" "2413" "G")
  (list "2480" "VH-BEDRIJFSVLOERPLAAT_STAAL_RIJPLAAT" 170 0.18 "CONTINUOUS" "2479" "G")
  (list "2481" "VH-BEDRIJFSVLOERPLAAT_STAAL_SCHEEPSHUID" 170 0.18 "CONTINUOUS" "2479" "G")
  (list "2476" "VH-BEDRIJFSVLOERPLAAT_BETON_INDUSTRIE" 170 0.18 "CONTINUOUS" "2475" "G")
  (list "2527" "VH-SPECIAAL_SPORT_ATLETIEKBAAN" 90 0.18 "CONTINUOUS" "2526" "G")
  (list "2528" "VH-SPECIAAL_SPORT_UNIVERSEELSPORTVELD" 90 0.18 "CONTINUOUS" "2526" "G")
  (list "2352" "VH-GOOT_BETON_PREFAB" 170 0.18 "CONTINUOUS" "2350" "G")
  (list "2351" "VH-GOOT_BETON_GESTORT" 170 0.18 "CONTINUOUS" "2350" "G")
  (list "2354" "VH-GOOT_BSS_ACHTERKANT" 170 0.18 "CONTINUOUS" "2353" "G")
  (list "2355" "VH-GOOT_BSS_VOORKANT" 170 0.18 "CONTINUOUS" "2353" "G")
  (list "2358" "VH-GOOT_STRAATBAKSTEEN_VOORKANT" 170 0.18 "CONTINUOUS" "2356" "G")
  (list "2357" "VH-GOOT_STRAATBAKSTEEN_ACHTERKANT" 170 0.18 "CONTINUOUS" "2356" "G")
  (list "2501" "VH-FUNDERING_SLAKKEN_AVI" 7 0.18 "CONTINUOUS" "2500" "G")
  (list "2502" "VH-FUNDERING_SLAKKEN_HOOGOVEN" 7 0.18 "CONTINUOUS" "2500" "G")
  (list "2497" "VH-FUNDERING_GRANULAAT_MENG" 7 0.18 "CONTINUOUS" "2495" "G")
  (list "2496" "VH-FUNDERING_GRANULAAT_BETON" 7 0.18 "CONTINUOUS" "2495" "G")
  (list "2943" "VH-GESLOTENVERHARDING_ASFALT_SLIJTLAAG_ROOD" 10 0.18 "CONTINUOUS" "2942" "G")
  (list "3012" "VH-GESLOTENVERHARDING_ASFALT_ONDERLAAG_1" 10 0.18 "CONTINUOUS" "3011" "G")
  (list "3013" "VH-GESLOTENVERHARDING_ASFALT_ONDERLAAG_2" 10 0.18 "CONTINUOUS" "3011" "G")
  (list "3016" "VH-GESLOTENVERHARDING_ASFALT_TUSSENLAAG_1" 10 0.18 "CONTINUOUS" "3015" "G")
  (list "3017" "VH-GESLOTENVERHARDING_ASFALT_TUSSENLAAG_2" 10 0.18 "CONTINUOUS" "3015" "G")
  (list "528" "VH-KANTOPSLUITING_ELEMENT_BOOMKRANS_ELEMENT" 60 0.18 "CONTINUOUS" "3392" "G")
  (list "2451" "VH-KANTOPSLUITING_TROTTOIRBAND_RWS_110 220" 210 0.18 "VH-RWSBAND-SO" "2450" "G")
  (list "2452" "VH-KANTOPSLUITING_TROTTOIRBAND_RWS_ZOAB" 210 0.18 "VH-RWSBAND-SO" "2450" "G")
  (list "2444" "VH-KANTOPSLUITING_TROTTOIRBAND_180X200_ZOAB" 210 0.18 "VH-TROTTOIRBAND-SO" "2443" "G")
  (list "2498" "VH-FUNDERING_GRANULAAT_MENG_HYDRAULISCH" 7 0.18 "CONTINUOUS" "2497" "G")
  (list "4032" "VH-GESLOTENVERHARDING_KUNSTSTOF" 10 0.18 "CONTINUOUS" "3342" "G")
  (list "4031" "VH-OPENVERHARDING_BETONELEMENT" 90 0.18 "CONTINUOUS" "2519" "G")
  (list "2513" "VH-HALFVERHARDING_SCHELP" 130 0.18 "CONTINUOUS" "2511" "G")
  (list "3509" "VH-ONVERHARD_BOOMSCHORS" 210 0.18 "CONTINUOUS" "2936" "G")
  (list "3510" "VH-ONVERHARD_ZAND" 210 0.18 "CONTINUOUS" "2936" "G")
  (list "2535" "VH-REPARATIES" 170 0.18 "CONTINUOUS" "" "")
  (list "2342" "VH-DREMPEL" 30 0.18 "CONTINUOUS" "" "")
  (list "2456" "VH-KANTVERHARDING" 60 0.18 "CONTINUOUS" "" "")
  (list "2360" "VH-KANTOPSLUITING" 7 0.18 "CONTINUOUS" "" "")
  (list "3343" "VH-KNIPLIJN" 251 0.18 "CONTINUOUS" "" "")
  (list "2474" "VH-BEDRIJFSVLOERPLAAT" 170 0.18 "CONTINUOUS" "" "")
  (list "2537" "VH-VERKANTING" 7 0.18 "CONTINUOUS" "" "")
  (list "2536" "VH-LEVENSDUURVERLENGENDE MAATREGEL" 170 0.18 "CONTINUOUS" "" "")
  (list "2462" "VH-MATERIAALGRENS" 7 0.18 "ZZ-HIDDEN-SO" "" "")
  (list "2519" "VH-OPENVERHARDING" 90 0.18 "CONTINUOUS" "" "")
  (list "2936" "VH-ONVERHARD" 210 0.18 "CONTINUOUS" "" "")
  (list "2445" "VH-KANTOPSLUITING_TROTTOIRBAND_180X200-OP DE KOP" 210 0.18 "VH-TROTTOIRBAND_OPKOP-SO" "2443" "G")
  (list "2441" "VH-KANTOPSLUITING_TROTTOIRBAND_130X150-OP DE KOP" 210 0.18 "VH-TROTTOIRBAND_OPKOP-SO" "2440" "G")
  (list "2448" "VH-KANTOPSLUITING_TROTTOIRBAND_280X300-OP DE KOP" 210 0.18 "VH-TROTTOIRBAND_OPKOP-SO" "2447" "G")
  (list "2465" "VH-GESLOTENVERHARDING_ASFALT_FREESVAK" 10 0.18 "CONTINUOUS" "2464" "G")
  (list "2530" "VH-OPENVERHARDING_STRAATBAKSTEEN-OP DE KOP" 7 0.25 "CONTINUOUS" "2529" "G")
  (list "2393" "VH-KANTOPSLUITING_GELEIDEBAND-OPNIEUW STELLEN" 7 0.25 "CONTINUOUS" "2386" "G/S")
  (list "2363" "VH-KANTOPSLUITING_BETONRUG" 7 0.25 "CONTINUOUS" "2360" "G")
  (list "2470" "VH-GESLOTENVERHARDING_ASFALT_ZAAGSNEDE" 7 0.25 "CONTINUOUS" "2464" "G")
  (list "2408" "VH-KANTOPSLUITING_OPSLUITBAND-OPNIEUW STELLEN" 7 0.25 "CONTINUOUS" "2397" "G")
  (list "2419" "VH-KANTOPSLUITING_RIJWIELPADBAND-OPNIEUW STELLEN" 7 0.25 "CONTINUOUS" "2416" "G")
  (list "2365" "VH-KANTOPSLUITING_BUSHALTEBAND-OPNIEUW STELLEN" 7 0.25 "CONTINUOUS" "2364" "G")
  (list "2432" "VH-KANTOPSLUITING_SCHEIDINGSBAND-OPNIEUW STELLEN" 7 0.25 "CONTINUOUS" "2422" "G")
  (list "2412" "VH-KANTOPSLUITING_PLATEAUBAND-OPNIEUW STELLEN" 7 0.25 "CONTINUOUS" "2410" "G")
  (list "4093" "VH-KANTOPSLUITING_ASFALTBAND-OPNIEUW STELLEN" 7 0.25 "CONTINUOUS" "4092" "G")
  (list "4030" "VH-KANTOPSLUITING_TROTTOIRBAND-OPNIEUW STELLEN" 7 0.25 "CONTINUOUS" "2439" "G")
  (list "2385" "VH-KANTOPSLUITING_GAZONBAND-OPNIEUW STELLEN" 7 0.25 "CONTINUOUS" "2377" "G")
  (list "2415" "VH-KANTOPSLUITING_PWSBAND-OPNIEUW STELLEN" 7 0.25 "CONTINUOUS" "2413" "G")
  (list "2454" "VH-KANTOPSLUITING_TROTTOIRBAND_RWS-OPNIEUW STELLEN" 7 0.25 "CONTINUOUS" "2450" "G")
  (list "2446" "VH-KANTOPSLUITING_TROTTOIRBAND_180X200-OPNIEUW STELLEN" 7 0.25 "CONTINUOUS" "2443" "G")
  (list "2442" "VH-KANTOPSLUITING_TROTTOIRBAND_130X150-OPNIEUW STELLEN" 7 0.25 "CONTINUOUS" "2440" "G")
  (list "2449" "VH-KANTOPSLUITING_TROTTOIRBAND_280X300-OPNIEUW STELLEN" 7 0.25 "CONTINUOUS" "2447" "G")
  (list "2453" "VH-KANTOPSLUITING_TROTTOIRBAND_RWS_ZOAB-OPNIEUW STELLEN" 7 0.25 "CONTINUOUS" "2452" "G")
)) *nlcs-layers*))

; Verkeersmaatregelen Vaarweg (VV) - 15 lagen
(setq *nlcs-layers* (cons (list "VV" "Verkeersmaatregelen Vaarweg" (list
  (list "4085" "VV-MARKERING_BETONNING" 170 0.18 "CONTINUOUS" "2540" "G/S")
  (list "2552" "VV-VAARGEBIED_SNEL" 10 0.18 "CONTINUOUS" "2551" "G")
  (list "2550" "VV-DOORVAART_HOOGTE" 7 0.18 "CONTINUOUS" "2548" "G")
  (list "2549" "VV-DOORVAART_BREEDTE" 7 0.18 "CONTINUOUS" "2548" "G")
  (list "2546" "VV-LIGPLAATS_GEVAARLIJKE LADING" 10 0.18 "CONTINUOUS" "2545" "G")
  (list "2541" "VV-MARKERING_BALLENLIJN" 170 0.18 "CONTINUOUS" "2540" "G")
  (list "2543" "VV-VERKEERSTEKEN_DRAAGCONSTRUCTIE" 7 0.18 "CONTINUOUS" "2542" "G")
  (list "2551" "VV-VAARGEBIED" 210 0.18 "CONTINUOUS" "" "G")
  (list "2945" "VV-SCHEPENTELLER" 170 0.18 "CONTINUOUS" "" "G")
  (list "2547" "VV-AFMEERLOKATIE" 140 0.18 "CONTINUOUS" "" "G")
  (list "2548" "VV-DOORVAART" 7 0.18 "CONTINUOUS" "" "G")
  (list "2992" "VV-PVR" 7 0.18 "CONTINUOUS" "" "G")
  (list "2545" "VV-LIGPLAATS" 140 0.18 "CONTINUOUS" "" "G")
  (list "2540" "VV-MARKERING" 170 0.18 "CONTINUOUS" "" "G")
  (list "2542" "VV-VERKEERSTEKEN" 170 0.18 "CONTINUOUS" "" "G")
)) *nlcs-layers*))

; Verkeersmaatregelen Weg (VW) - 96 lagen
(setq *nlcs-layers* (cons (list "VW" "Verkeersmaatregelen Weg" (list
  (list "2638" "VW-VERKEERSTEKEN_BORD" 7 0.18 "CONTINUOUS" "2637" "G/S")
  (list "4101" "VW-VERKEERSTEKEN_TRAMSIGNALERING" 7 0.18 "CONTINUOUS" "2637" "G/S")
  (list "2640" "VW-VERKEERSTEKEN_DRAAGCONSTRUCTIE" 7 0.18 "CONTINUOUS" "2637" "G/S")
  (list "2639" "VW-VERKEERSTEKEN_BEBAKENING" 7 0.18 "CONTINUOUS" "2637" "G/S")
  (list "2573" "VW-MARKERING_SYMBOOL" 7 0.18 "CONTINUOUS" "2569" "G/S")
  (list "2570" "VW-MARKERING_PIJL" 7 0.18 "CONTINUOUS" "2569" "G/S")
  (list "2564" "VW-BEWEGWIJZERING_DRAAGCONSTRUCTIE" 7 0.18 "CONTINUOUS" "2553" "G/S")
  (list "3344" "VW-AFZETTING_POLLER" 7 0.18 "CONTINUOUS" "2657" "G/S")
  (list "3473" "VW-AFZETTING_AFSLUITPAAL" 7 0.18 "CONTINUOUS" "2657" "G/S")
  (list "3351" "VW-VERKEERSSPIEGEL_DRAAGCONSTRUCTIE" 7 0.18 "CONTINUOUS" "3350" "G/S")
  (list "2619" "VW-MARKERING_DWARS_DRIEHOEK" 7 0.18 "VW-HAAIETAND50_L" "2618" "G/S")
  (list "3348" "VW-AFZETTING_POLLER_VAST" 7 0.18 "CONTINUOUS" "3344" "G/S")
  (list "3347" "VW-AFZETTING_POLLER_SCANPAAL" 7 0.18 "CONTINUOUS" "3344" "G/S")
  (list "3345" "VW-AFZETTING_POLLER_BEWEEGBAAR" 7 0.18 "CONTINUOUS" "3344" "G/S")
  (list "2631" "VW-MARKERING_DWARS_OVERSTEEK_KANALISATIESTREEP50" 7 0.13 "VW-5050_STREEP" "2629" "G/S")
  (list "2635" "VW-MARKERING_DWARS_OVERSTEEK_BLOKSTREEP" 7 0.5 "VW-BLOK50" "2629" "G/S")
  (list "2601" "VW-MARKERING_LANGS_STREEP_39" 7 0.13 "VW-39_STREEP" "2579" "G/S")
  (list "3551" "VW-MARKERING_LANGS_STREEP_050050" 7 0.13 "VW-5050_STREEP" "2579" "G/S")
  (list "2592" "VW-MARKERING_LANGS_STREEP_13" 7 0.13 "VW-13_STREEP" "2579" "G/S")
  (list "2589" "VW-MARKERING_LANGS_STREEP_11" 7 0.13 "VW-11_STREEP" "2579" "G/S")
  (list "2610" "VW-MARKERING_LANGS_STREEP_27030" 7 0.13 "VW-27030_STREEP" "2579" "G/S")
  (list "2599" "VW-MARKERING_LANGS_STREEP_33" 7 0.13 "VW-33_STREEP" "2579" "G/S")
  (list "2597" "VW-MARKERING_LANGS_STREEP_31" 7 0.13 "VW-31_STREEP" "2579" "G/S")
  (list "2605" "VW-MARKERING_LANGS_STREEP_91" 7 0.25 "VW-91_STREEP" "2579" "G/S")
  (list "2607" "VW-MARKERING_LANGS_STREEP_93" 7 0.13 "VW-93_STREEP" "2579" "G/S")
  (list "2612" "VW-MARKERING_LANGS_STREEP_30270" 7 0.13 "VW-30270_STREEP" "2579" "G/S")
  (list "2632" "VW-MARKERING_DWARS_OVERSTEEK_KANALISATIESTREEP50_010" 7 0.13 "VW-5050_STREEP" "2631" "G/S")
  (list "3550" "VW-MARKERING_DWARS_OVERSTEEK_KANALISATIESTREEP50_020" 7 0.18 "VW-5050_STREEP" "2631" "G/S")
  (list "2604" "VW-MARKERING_LANGS_STREEP_39_030" 7 0.25 "VW-39_STREEP" "2601" "G/S")
  (list "2602" "VW-MARKERING_LANGS_STREEP_39_010" 7 0.13 "VW-39_STREEP" "2601" "G/S")
  (list "2603" "VW-MARKERING_LANGS_STREEP_39_015" 7 0.13 "VW-39_STREEP" "2601" "G/S")
  (list "3552" "VW-MARKERING_LANGS_STREEP_050050_010" 7 0.13 "VW-5050_STREEP" "3551" "G/S")
  (list "2595" "VW-MARKERING_LANGS_STREEP_13_030" 7 0.25 "VW-13_STREEP" "2592" "G/S")
  (list "2594" "VW-MARKERING_LANGS_STREEP_13_020" 7 0.18 "VW-13_STREEP" "2592" "G/S")
  (list "2593" "VW-MARKERING_LANGS_STREEP_13_010" 7 0.13 "VW-13_STREEP" "2592" "G/S")
  (list "3018" "VW-MARKERING_LANGS_STREEP_13_015" 7 0.13 "VW-13_STREEP" "2592" "G/S")
  (list "2596" "VW-MARKERING_LANGS_STREEP_13_045" 7 0.5 "VW-13_STREEP" "2592" "G/S")
  (list "2590" "VW-MARKERING_LANGS_STREEP_11_010" 7 0.13 "VW-11_STREEP" "2589" "G/S")
  (list "2591" "VW-MARKERING_LANGS_STREEP_11_015" 7 0.13 "VW-11_STREEP" "2589" "G/S")
  (list "2611" "VW-MARKERING_LANGS_STREEP_27030_010" 7 0.13 "VW-27030_STREEP" "2610" "G/S")
  (list "3019" "VW-MARKERING_LANGS_STREEP_27030_015" 7 0.13 "VW-27030_STREEP" "2610" "G/S")
  (list "2600" "VW-MARKERING_LANGS_STREEP_33_015" 7 0.13 "VW-33_STREEP" "2599" "G/S")
  (list "2598" "VW-MARKERING_LANGS_STREEP_31_010" 7 0.13 "VW-31_STREEP" "2597" "G/S")
  (list "3553" "VW-MARKERING_LANGS_STREEP_91_010" 7 0.13 "VW-91_STREEP" "2605" "G/S")
  (list "2606" "VW-MARKERING_LANGS_STREEP_91_030" 7 0.25 "VW-91_STREEP" "2605" "G/S")
  (list "3549" "VW-MARKERING_LANGS_STREEP_93_030" 7 0.25 "VW-93_STREEP" "2607" "G/S")
  (list "2608" "VW-MARKERING_LANGS_STREEP_93_010" 7 0.13 "VW-93_STREEP" "2607" "G/S")
  (list "2613" "VW-MARKERING_LANGS_STREEP_30270_010" 7 0.13 "VW-30270_STREEP" "2612" "G/S")
  (list "3020" "VW-MARKERING_LANGS_STREEP_30270_015" 7 0.13 "VW-30270_STREEP" "2612" "G/S")
  (list "2553" "VW-BEWEGWIJZERING" 7 0.18 "CONTINUOUS" "" "")
  (list "2641" "VW-HECTOMETRERING" 7 0.18 "CONTINUOUS" "" "")
  (list "3350" "VW-VERKEERSSPIEGEL" 7 0.18 "CONTINUOUS" "" "")
  (list "2572" "VW-MARKERING_PUNTSTUK" 7 0.18 "CONTINUOUS" "2569" "G")
  (list "2618" "VW-MARKERING_DWARS" 7 0.18 "CONTINUOUS" "2569" "G")
  (list "2577" "VW-MARKERING_ACTIEF" 7 0.18 "CONTINUOUS" "2569" "G")
  (list "2578" "VW-MARKERING_LANGS" 7 0.18 "CONTINUOUS" "2569" "G")
  (list "2571" "VW-MARKERING_VERDRIJFSTREEP" 7 0.18 "CONTINUOUS" "2569" "G")
  (list "2575" "VW-MARKERING_AFGEKRUISTVLAK" 7 0.18 "CONTINUOUS" "2569" "G")
  (list "2559" "VW-BEWEGWIJZERING_FIETS" 7 0.18 "CONTINUOUS" "2553" "G")
  (list "2554" "VW-BEWEGWIJZERING_ERFTOEGANGSWEG" 7 0.18 "CONTINUOUS" "2553" "G")
  (list "2555" "VW-BEWEGWIJZERING_GEBIEDSONTSLUITINGWEG" 7 0.18 "CONTINUOUS" "2553" "G")
  (list "2561" "VW-BEWEGWIJZERING_VOETGANGER" 7 0.18 "CONTINUOUS" "2553" "G")
  (list "2556" "VW-BEWEGWIJZERING_STROOMWEG" 7 0.18 "CONTINUOUS" "2553" "G")
  (list "2560" "VW-BEWEGWIJZERING_BROMFIETS" 7 0.18 "CONTINUOUS" "2553" "G")
  (list "2563" "VW-BEWEGWIJZERING_NIETGEINTEGREERD" 7 0.18 "CONTINUOUS" "2553" "G")
  (list "2623" "VW-MARKERING_DWARS_STOPSTREEP" 7 0.18 "CONTINUOUS" "2618" "G")
  (list "2629" "VW-MARKERING_DWARS_OVERSTEEK" 7 0.18 "CONTINUOUS" "2618" "G")
  (list "3554" "VW-MARKERING_DWARS_STREEP" 7 0.18 "CONTINUOUS" "2618" "G")
  (list "2579" "VW-MARKERING_LANGS_STREEP" 7 0.18 "CONTINUOUS" "2578" "G")
  (list "2565" "VW-BEWEGWIJZERING_DRAAGCONSTRUCTIE_PORTAAL" 7 0.18 "CONTINUOUS" "2564" "G")
  (list "2567" "VW-BEWEGWIJZERING_DRAAGCONSTRUCTIE_UITHOUDER" 7 0.18 "CONTINUOUS" "2564" "G")
  (list "2558" "VW-BEWEGWIJZERING_STROOMWEG_REGIONAAL" 7 0.18 "CONTINUOUS" "2556" "G")
  (list "2557" "VW-BEWEGWIJZERING_STROOMWEG_NATIONAAL" 7 0.18 "CONTINUOUS" "2556" "G")
  (list "3346" "VW-AFZETTING_POLLER_PUT" 7 0.18 "CONTINUOUS" "3344" "G")
  (list "2624" "VW-MARKERING_DWARS_STOPSTREEP_020" 7 0.18 "CONTINUOUS" "2623" "G")
  (list "2625" "VW-MARKERING_DWARS_STOPSTREEP_030" 7 0.25 "CONTINUOUS" "2623" "G")
  (list "2627" "VW-MARKERING_DWARS_STOPSTREEP_015" 7 0.13 "CONTINUOUS" "2623" "G")
  (list "2626" "VW-MARKERING_DWARS_STOPSTREEP_050" 7 0.5 "CONTINUOUS" "2623" "G")
  (list "2630" "VW-MARKERING_DWARS_OVERSTEEK_VOETGANGERS" 7 0.18 "CONTINUOUS" "2629" "G")
  (list "2580" "VW-MARKERING_LANGS_STREEP_DOORGETROKKEN" 7 0.13 "CONTINUOUS" "2579" "G")
  (list "2566" "VW-BEWEGWIJZERING_DRAAGCONSTRUCTIE_PORTAAL_POER" 7 0.18 "CONTINUOUS" "2565" "G")
  (list "2568" "VW-BEWEGWIJZERING_DRAAGCONSTRUCTIE_UITHOUDER_POER" 7 0.18 "CONTINUOUS" "2567" "G")
  (list "2585" "VW-MARKERING_LANGS_STREEP_DOORGETROKKEN_045" 7 0.5 "CONTINUOUS" "2580" "G")
  (list "2583" "VW-MARKERING_LANGS_STREEP_DOORGETROKKEN_015" 7 0.13 "CONTINUOUS" "2580" "G")
  (list "2581" "VW-MARKERING_LANGS_STREEP_DOORGETROKKEN_005" 7 0.13 "CONTINUOUS" "2580" "G")
  (list "2582" "VW-MARKERING_LANGS_STREEP_DOORGETROKKEN_010" 7 0.13 "CONTINUOUS" "2580" "G")
  (list "2584" "VW-MARKERING_LANGS_STREEP_DOORGETROKKEN_020" 7 0.18 "CONTINUOUS" "2580" "G")
  (list "2637" "VW-VERKEERSTEKEN" 7 0.18 "CONTINUOUS" "" "")
  (list "2569" "VW-MARKERING" 7 0.18 "CONTINUOUS" "" "")
  (list "3349" "VW-BLINDENGELEIDEROUTE" 30 0.18 "CONTINUOUS" "" "")
  (list "2659" "VW-RIJRICHTING" 7 0.18 "CONTINUOUS" "" "")
  (list "2656" "VW-VERKANTING" 80 0.18 "CONTINUOUS" "" "")
  (list "2948" "VW-VERKEERSTELLER" 160 0.18 "CONTINUOUS" "" "")
  (list "2658" "VW-OMLEIDINGSROUTE" 40 0.18 "CONTINUOUS" "" "")
  (list "2655" "VW-PVR" 10 0.18 "CONTINUOUS" "" "")
  (list "2657" "VW-AFZETTING" 7 0.18 "CONTINUOUS" "" "")
)) *nlcs-layers*))

; Waterhuishouding (WH) - 0 lagen
(setq *nlcs-layers* (cons (list "WH" "Waterhuishouding" (list
)) *nlcs-layers*))

; Diversen (ZZ) - 33 lagen
(setq *nlcs-layers* (cons (list "ZZ" "Diversen" (list
  (list "9" "ZZ-HOOGTELABEL_KANTOPSLUITING" 7 0.25 "CONTINUOUS" "8" "G/S")
  (list "8" "ZZ-HOOGTELABEL" 7 0.25 "CONTINUOUS" "" "G/S")
  (list "3362" "ZZ-PEIL_PEILBOUT" 7 0.18 "CONTINUOUS" "3358" "G")
  (list "3359" "ZZ-PEIL_ADVIESBOUWPEIL" 7 0.18 "CONTINUOUS" "3358" "G")
  (list "3360" "ZZ-PEIL_GEINTERPOLEERD" 7 0.18 "CONTINUOUS" "3358" "G")
  (list "3361" "ZZ-PEIL_INGEMETEN" 7 0.18 "CONTINUOUS" "3358" "G")
  (list "3363" "ZZ-PEIL_UITGIFTE" 7 0.18 "CONTINUOUS" "3358" "G")
  (list "571" "ZZ-GRENS_ONDERZOEKSGEBIED" 7 0.18 "ZZ-ONDERZOEKSGRENS-SO" "4086" "G")
  (list "619" "ZZ-GRENS_WERK" 7 0.35 "ZZ-WERKGRENS-SO" "4086" "G")
  (list "617" "ZZ-GRENS_PROJECT" 7 0.35 "ZZ-PROJECTGRENS-SO" "4086" "G")
  (list "618" "ZZ-GRENS_SYSTEEMGRENS" 7 0.35 "ZZ-SYSTEEMGRENS-SO" "4086" "G")
  (list "3358" "ZZ-PEIL" 7 0.18 "CONTINUOUS" "" "G")
  (list "2708" "ZZ-DETAIL2" 7 0.25 "CONTINUOUS" "" "G")
  (list "2706" "ZZ-NAP" 7 0.18 "AL-NAP_LIJN-SO" "" "G")
  (list "4086" "ZZ-GRENS" 7 0.18 "CONTINUOUS" "" "G")
  (list "2699" "ZZ-(M)" 7 0.18 "CONTINUOUS" "" "M")
  (list "2695" "ZZ-(T3.0)" 160 0.35 "CONTINUOUS" "" "T30")
  (list "2694" "ZZ-(T2.5)" 7 0.25 "CONTINUOUS" "" "T25")
  (list "2693" "ZZ-(T1.8)" 10 0.18 "CONTINUOUS" "" "T18")
  (list "2703" "ZZ-CONSTRUCTIELIJN" 7 0.18 "CONTINUOUS" "" "G")
  (list "3357" "ZZ-HULPLIJN" 7 0.18 "CONTINUOUS" "" "G")
  (list "2711" "ZZ-DETAIL5" 7 0.7 "CONTINUOUS" "" "G")
  (list "2701" "ZZ-AFBREEKLIJN" 7 0.18 "ZZ-AFBREEK-SO" "" "G")
  (list "2700" "ZZ-AANPIJLING" 7 0.18 "CONTINUOUS" "" "G")
  (list "2710" "ZZ-DETAIL4" 7 0.5 "CONTINUOUS" "" "G")
  (list "2707" "ZZ-DETAIL1" 7 0.18 "CONTINUOUS" "" "G")
  (list "2696" "ZZ-(T3.5)" 50 0.35 "CONTINUOUS" "" "T35")
  (list "2709" "ZZ-DETAIL3" 7 0.35 "CONTINUOUS" "" "G")
  (list "2704" "ZZ-STRAMIENLIJN" 7 0.18 "ZZ-STRAMIEN-SO" "" "G")
  (list "2702" "ZZ-HARTLIJN" 7 0.18 "ZZ-HART-SO" "" "G")
  (list "2697" "ZZ-(T5.0)" 130 0.5 "CONTINUOUS" "" "T50")
  (list "2698" "ZZ-(T7.0)" 210 0.7 "CONTINUOUS" "" "T70")
  (list "616" "ZZ-GRENS_FASE" 7 0.35 "ZZ-FASEGRENS-SO" "4086" "G")
)) *nlcs-layers*))

; Helper functions
(defun nlcs-get-discipline-name (code)
  (cdr (assoc code *nlcs-disciplines*)))

(defun nlcs-get-layers-for-discipline (code)
  (cdr (assoc code *nlcs-layers*)))

(defun nlcs-create-layer (discipline-code layer-name / layer full-name)
  ; Create a NLCS layer with correct properties
  (setq full-name (strcat discipline-code "-" layer-name))
  (command "-LAYER" "MAKE" full-name)
  full-name
)

(princ "\n[NLCS] Layer data geladen. ")
(princ "3618 lagen beschikbaar voor 31 disciplines.\n")
